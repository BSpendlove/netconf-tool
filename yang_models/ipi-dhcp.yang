/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-dhcp.yang
*
*/

module ipi-dhcp {

    yang-version 1.1;

    namespace   "http://www.ipinfusion.com/yang/ocnos/ipi-dhcp";

    prefix "ipi-dhcp";

    import ipi-dhcp-relay-types {
        prefix ipi-dhcp-relay-types;
        revision-date 2021-09-03;
    }

    import ietf-inet-types {
        prefix inet;
        revision-date 2013-07-15;
    }

    import ipi-dhcp-snooping-types {
        prefix ipi-dhcp-snooping-types;
        revision-date 2021-12-07;
    }

    include ipi-dhcp-relay { revision-date 2021-11-30;}
    include ipi-dhcp-client { revision-date 2021-11-16;}
    include ipi-dhcp-snooping { revision-date 2021-12-10;}
    include ipi-dhcp-snooping-interface { revision-date 2021-12-07;}
    organization
        "IP Infusion Inc.";

    contact
        "Address: 3965 Freedom Circle, Suite 200, Santa Clara, CA 95054
         Phone: +1 408-400-1900
         E-mail: support@ipinfusion.com
         Web: http://www.ipinfusion.com/";

    description
        "feature_dhcp_configuration";


    revision "2021-12-10" {
        description "Add import to DHCP snooping types yang file";
        reference " 0.8.0.";
    }

    revision "2021-12-07" {
        description "Add dhcp-snooping as a sub-module.";
        reference " 0.7.0.";
    }

    revision "2021-11-30" {
        description "Updated in its sub-module ipi-dhcp-relay";
        reference " 0.6.0.";
    }

    revision "2021-11-17" {
        description "Updated in its sub-module ipi-dhcp-client";
        reference " 0.5.0.";
    }

    revision "2021-09-03" {
        description "Update descriptions of attribute";
        reference " 0.4.0.";
    }

    revision "2021-06-11" {
        description "Changes to support DHCP L3VPN feature";
        reference " 0.3.0.";
    }

    revision "2021-04-01" {
        description "Included new attributes as part of DHCPv6 Relay PD Auto Route injection feature";
        reference " 0.3.0.";
    }

    revision "2020-12-15" {
        description "Change to have data-types in lower case instead of camel case";
        reference " 0.2.0.";
    }

    revision "2020-08-11" {
        description "Initial Version";
        reference " 0.1.0.";
    }

    grouping dhcp-feature-config {
        description
            "Configuration data for feature-dhcp for client and relay";
        leaf disable-dhcp-feature  {
            type  empty;
            description "Disable the DHCP client and DHCP relay on the device.";
        } // END of disable-dhcp-feature definition.

    } // END of dhcp-feature-config definition.
    grouping dhcp-global-top {
        description
            "DHCP global level information grouping";
        container global {
            description
                "DHCP global level information";
            container config {
                description
                    "Configurationd data for feature dhcp";
                uses dhcp-feature-config;
            } // END of config-container definition.
            container state {
                config false;
                description
                    "Operational state data";
                uses dhcp-feature-config;
            } // END of state-container definition.
        } // END of global-container definition.
    } // END of dhcp-global-top definition.

    grouping  dhcp-grouping {
    description
        "Enable feature dhcp";
    container dhcp {
        description
            "Enable feature dhcp";
        uses dhcp-global-top;
        uses relay-grouping;
        uses client-grouping;
        uses snooping-grouping;
    } // END of dhcp-container definition.
    } // END of dhcp-grouping definition.

    uses dhcp-grouping;

    rpc clear-relay-stats {
        description "Use this RPC to clear dhcp relay statistics";
    }

    rpc clear-relay-option-stats {
        description "Use this RPC to clear dhcp relay option82 statistics";
    }

    rpc clear-dhcpv6-pd-route {
        description "Use this RPC to clear the DHCP routes";
        input  {
            leaf vrf-name  {
                type string;
                mandatory true;
                description "";
            }
        }
    }

    rpc dhcp-snooping-write-database {
        description "Save DHCP snooping bind table";
        input  {
            leaf bridge-id  {
                type string {
                    length "1..32";
                }
                mandatory true;
                description "Bridge group number";
            }
        }
    }

    rpc dhcp-snooping-renew-database {
        description "Rebuild DHCP snooping bind table entries for IPv4 and IPv6";
        input  {
            leaf bridge-id  {
                type string {
                    length "1..32";
                }
                mandatory true;
                description "Bridge group number";
            }
        }
    }

    rpc dhcp-snooping-write-source-binding-database {
        description "Save DHCP snooping source guard bind table";
        input  {
            leaf bridge-id  {
                type string {
                    length "1..32";
                }
                mandatory true;
                description "Bridge group number";
            }
        }
    }

    rpc dhcp-snooping-renew-source-database {
        description "Rebuild DHCP snooping source guard bind table entries for IPv4 and
                    IPv6";
        input  {
            leaf bridge-id  {
                type string {
                    length "1..32";
                }
                mandatory true;
                description "Bridge group number";
            }
        }
    }

    rpc dhcp-snooping-clear-source-binding-database {
        description "Clear DHCP snooping source guard binding table entries";
        input  {
            leaf bridge-id  {
                type string {
                    length "1..32";
                }
                mandatory true;
                description "Bridge group number";
            }
        }
    }

    rpc dhcp-snooping-clear-database {
        description "Clear DHCP snooping binding table entries";
        input  {
            leaf bridge-id  {
                type string {
                    length "1..32";
                }
                mandatory true;
                description "Bridge group number";
            }
        }
    }

    rpc dhcp-snooping-terminal-debug-on {
        description "DHCP snooping enable debug terminal";
        input  {
            leaf options  {
                type ipi-dhcp-snooping-types:dhcp_snooping_debug_t;
                mandatory true;
                description "Enable debug on DHCP snooping feature";
            }
        }
    }

    rpc dhcp-snooping-terminal-debug-off {
        description "DHCP snooping disable debug terminal";
        input  {
            leaf options  {
                type ipi-dhcp-snooping-types:dhcp_snooping_debug_t;
                mandatory true;
                description "Disable debug on DHCP snooping feature";
            }
        }
    }

    notification dhcpv6-relay-pd-route {

        description "Notification when PD injected routes are added/deleted.";

        // severity "INFO";
        // eventClass "STATE";
        leaf vrf-name {
            type  string;
        description
            "VPN routing/forwarding Instance name";
        }

        leaf interface-name {
            type  string;
        description
            "DHCP client facing interface, which is part of the LAN network";
        }

        leaf state {
            type ipi-dhcp-relay-types:dhcp6_pd_route_state_t;
        description
            "Notification route add/delete input";
        }

        leaf prefix {
            type  inet:ipv6-prefix;
        description
            "Delegated prefix";
        }

        leaf next-hop {
            type  inet:ipv6-address;
        description
            "DHCP client interface linklocal adddress";
        }
    }

}

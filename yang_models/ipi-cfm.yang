/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-cfm.yang
*
*/

module ipi-cfm {

    yang-version 1.1;

    namespace   "http://www.ipinfusion.com/yang/ocnos/ipi-cfm";

    prefix "ipi-cfm";

    import ipi-cfm-data-types {
        prefix ipi-cfm-data-types;
        revision-date 2018-12-06;
    }

    import feature-list {
        prefix feature-list;
        revision-date 2022-07-13;
    }

    include ipi-cfm-common { revision-date 2022-04-22;}
    include ipi-cfm-y1731 { revision-date 2021-12-09;}
    organization
        "IP Infusion Inc.";

    contact
        "Address: 3965 Freedom Circle, Suite 200, Santa Clara, CA 95054
         Phone: +1 408-400-1900
         E-mail: support@ipinfusion.com
         Web: http://www.ipinfusion.com/";

    description
        "Data model for IPI CFM Configuration and Operational state";


    revision "2022-04-25" {
        description "Suncom patch merge";
        reference " 0.1.3.";
    }

    revision "2022-04-04" {
        description "Added if-feature in mo_ipi-cfm-common.xml";
        reference " 0.3.0.";
    }

    revision "2021-12-20" {
        description "Made bridge-id attribute optional for MD object to remove bridge dependency for L2/VLAN CFM";
        reference " 0.1.2.";
    }

    revision "2021-12-15" {
        description "Removed skip-yang as FW dependency is resolved";
        reference " 0.1.1.";
    }

    revision "2021-12-09" {
        description "Initial Version";
        reference " 0.1.0.";
    }

    grouping cfm-global-config {
        description
            "Grouping for Global CFM attributes";
        leaf debug  {
            type  ipi-cfm-data-types:cfm_debug_t;
            description "This attribute enables debugging for CFM";
        } // END of debug definition.

    } // END of cfm-global-config definition.
    grouping cfm-terminal-debug-state {
        description
            "Grouping for CFM terminal Debug attributes";
        leaf terminal-debug  {
            type  ipi-cfm-data-types:cfm_debug_t;
            description "This attribute describes the CFM terminal debug status";
        } // END of terminal-debug definition.

    } // END of cfm-terminal-debug-state definition.
    grouping cfm-mep-ccm-top {
        description
            "Grouping for CFM MEP Continuity Check Messages";
        container continuity-check {
            description
                "Enclosing container for the list of CFM MEP Continuity Check Messages";
            container config {
                description
                    "Configuration data for CFM MEP Continuity Check Message";
                uses cfm-mep-ccm-config;
            } // END of config-container definition.
            container state {
                config false;
                description
                    "Operational data for CFM MEP Continuity Check Message";
                uses cfm-mep-ccm-config;
                uses cfm-mep-ccm-state;
            } // END of state-container definition.
            uses cfm-remote-meps-top;
        } // END of continuity-check-container definition.
    } // END of cfm-mep-ccm-top definition.
    grouping cfm-meps-top {
        description
            "Grouping for CFM Maintenence End Points";
        container maintenance-end-points {
            description
                "Enclosing container for the list of Maintenence End Points";

            list maintenance-end-point {
            when " /ipi-cfm:cfm/ipi-cfm:maintenance-domains/ipi-cfm:maintenance-domain/ipi-cfm:maintenance-associations/ipi-cfm:maintenance-association/ipi-cfm:maintenance-end-points/ipi-cfm:maintenance-end-point/ipi-cfm:config/ipi-cfm:interface-name ";
                key "mep-id";
                description
                    "List of Maintenence End Points";
                leaf mep-id  {
                    type  leafref {
                        path  "../config/mep-id";
                    }
                    description "Integer that is unique among all the MEPs in the same MA. Other
                                definition is: a small integer, unique over a given Maintenance
                                Association, identifying a specific Maintenance association End Point";
                } // END of mep-id definition.

                container config {
                    description
                        "Configuration data for Maintenence End Point";
                    uses cfm-mep-config;
                } // END of config-container definition.
                container state {
                    config false;
                    description
                        "Operational data for Maintenence End Point";
                    uses cfm-mep-config;
                    uses cfm-mep-state;
                } // END of state-container definition.
                uses cfm-mep-ccm-top;
            } // End of maintenance-end-point-list
        } // END of maintenance-end-points-container definition.
    } // END of cfm-meps-top definition.
    grouping cfm-mas-top {
        description
            "Grouping for CFM Maintenence Assosiations";
        container maintenance-associations {
            description
                "Enclosing container for the list of Maintenence associations";

            list maintenance-association {
            when " /ipi-cfm:cfm/ipi-cfm:maintenance-domains/ipi-cfm:maintenance-domain/ipi-cfm:maintenance-associations/ipi-cfm:maintenance-association/ipi-cfm:config/ipi-cfm:vlan-id  or /ipi-cfm:cfm/ipi-cfm:maintenance-domains/ipi-cfm:maintenance-domain/ipi-cfm:maintenance-associations/ipi-cfm:maintenance-association/ipi-cfm:config/ipi-cfm:link-level-ma ";
                key "ma-name";
                description
                    "List of Maintenence associations";
                leaf ma-name  {
                    type  leafref {
                        path  "../config/ma-name";
                    }
                    description "The value union for the Maintenance Association Name.";
                } // END of ma-name definition.

                container config {
                    description
                        "Configuration data for Maintenence association";
                    uses cfm-ma-config;
                } // END of config-container definition.
                container state {
                    config false;
                    description
                        "Operational data for Maintenence association";
                    uses cfm-ma-config;
                } // END of state-container definition.
                uses cfm-meps-top;
                uses cfm-ma-default-mips-top;
            } // End of maintenance-association-list
        } // END of maintenance-associations-container definition.
    } // END of cfm-mas-top definition.
    grouping cfm-mds-top {
        description
            "Grouping for CFM Maintenence Domains";
        container maintenance-domains {
            description
                "Enclosing container for the list of Maintenence Domains";

            list maintenance-domain {
                key "md-name";
                description
                    "List of Maintenence Domains";
                leaf md-name  {
                    type  leafref {
                        path  "../config/md-name";
                    }
                    description "A unique identifier of a Maintenance Domain";
                } // END of md-name definition.

                container config {
                    description
                        "Configuration data for Maintenence Domain";
                    uses cfm-md-config;
                } // END of config-container definition.
                container state {
                    config false;
                    description
                        "Operational data for Maintenence Domain";
                    uses cfm-md-config;
                } // END of state-container definition.
                uses cfm-mas-top;
            } // End of maintenance-domain-list
        } // END of maintenance-domains-container definition.
    } // END of cfm-mds-top definition.
    grouping cfm-global-top {
        description
            "Grouping for CFM Global Configurations";
        container global {
            description
                "Global CFM container";
            container config {
                description
                    "CFM Global Configuration data";
                uses cfm-global-config;
            } // END of config-container definition.
            container state {
                config false;
                description
                    "CFM Global Operational data";
                uses cfm-global-config;
                uses cfm-terminal-debug-state;
            } // END of state-container definition.
        } // END of global-container definition.
    } // END of cfm-global-top definition.

    grouping  cfm-grouping {
    description
        "Top level container for Ethernet Connectivity Fault Management";
    container cfm {
        if-feature feature-list:HAVE_CFM;
        description
            "Top level container for Ethernet Connectivity Fault Management";
        uses cfm-global-top;
        uses cfm-mds-top;
    } // END of cfm-container definition.
    } // END of cfm-grouping definition.

    uses cfm-grouping;

    rpc cfm-clear-ethernet-remote-meps-per-domain-per-bridge {
        description "Use this RPC to clear ethernet CFM remote MEPs of specified domain and
                    bridge";
        input  {
            leaf bridge-id  {
                type string;
                mandatory true;
                description "This parameter indicates which bridge this maintenance domain will be
                            augumented to.";
            }
            leaf domain-name  {
                type string;
                mandatory true;
                description "A unique identifier of a Maintenance Domain";
            }
        }
    }

    rpc cfm-clear-all-mep-stats {
        description "Clear CFM statistics of all MEPs";
    }

    rpc cfm-clear-mep-stats-per-domain-per-vlan-per-bridge {
        description "Clear CFM statistics of specified MEP";
        input  {
            leaf bridge-id  {
                type string;
                mandatory true;
                description "This parameter indicates which bridge this maintenance domain will be
                            augumented to.";
            }
            leaf domain-name  {
                type string;
                mandatory true;
                description "A unique identifier of a Maintenance Domain";
            }
            leaf mep-id  {
                type uint16;
                mandatory true;
                description "Integer that is unique among all the MEPs in the same MA. Other
                            definition is: a small integer, unique over a given Maintenance
                            Association, identifying a specific Maintenance association End Point";
            }
            leaf vlan-id  {
                type uint16;
                mandatory true;
                description "The Primary VID of the MEP. This is the MA's vlan-id which is used
                            for frame tramsnit";
            }
        }
    }

    rpc cfm-snmp-restart {
        description "CFM SNMP restart";
    }

    rpc cfm-terminal-debug-enable {
        description "Use this RPC to set CFM debug options in EXEC mode";
        input  {
            leaf debug-options  {
                type ipi-cfm-data-types:cfm_debug_t;
                mandatory true;
                description "Debug configuration flag";
            }
        }
    }

    rpc cfm-terminal-debug-disable {
        description "Use this RPC to unset CFM debug options in EXEC mode";
        input  {
            leaf debug-options  {
                type ipi-cfm-data-types:cfm_debug_t;
                mandatory true;
                description "Debug configuration flag";
            }
        }
    }

    notification cfm-mep-ccm-highest-fault-info {

        description "Notify the highest CCM fault received to all notification clients like CLI, NETCONF and SNMP.";

        // severity "MINOR";
        // eventClass "STATE";
        leaf mep-id {
            type  uint16;
        description
            "Integer that is unique among all the MEPs in the same MA. Other
                    definition is: a small integer, unique over a given Maintenance
                    Association, identifying a specific Maintenance association End Point";
        }

        leaf ma-name {
            type  string;
        description
            "The value union for the Maintenance Association Name.";
        }

        leaf md-name {
            type  string;
        description
            "A unique identifier of a Maintenance Domain";
        }

        leaf highest-priority-defect-found {
            type ipi-cfm-data-types:cfm_mep_highest_fault_defect_t;
        description
            "Value indicating the highest-priority defect that has been present
                    since the MEP Fault Notification Generator state machine was last in
                    the FNG_RESET state. The non-existence of this leaf represents that no
                    defect has been present since the last FNG_RESET state.";
        }
    }

}

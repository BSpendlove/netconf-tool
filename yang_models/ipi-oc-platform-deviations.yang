module ipi-oc-platform-deviations {
  namespace "http://www.ipinfusion.com/yang/ocnos/ipi-oc-platform-deviations";
  prefix "ipi-oc-platform-deviations";

  import openconfig-platform {
      prefix oc-platform;
  }

  import openconfig-platform-psu {
      prefix oc-platform-psu;
  }

  import openconfig-platform-transceiver {
      prefix oc-platform-transceiver;
  }

  import openconfig-platform-port {
      prefix oc-port;
  }

  revision "2022-01-19" {
    description "Added new deviations for not supported trees";
  }

  revision "2021-05-07" {
      description
        "Added support to component parent, then not supported was removed.
         Added more deviations for transceiver attributes.";
  }

  revision "2021-01-29" {
      description
        "First release: add a type deviation for mfg-date";
  }

  deviation /oc-platform:components/oc-platform:component/oc-platform:power-supply/oc-platform:state/oc-platform-psu:output-voltage {
      deviate replace {
          type decimal64 {
              fraction-digits 2;
          }
      }
  }

  deviation /oc-platform:components/oc-platform:component/oc-platform:power-supply/oc-platform:state/oc-platform-psu:capacity {
      deviate replace {
          type decimal64 {
              fraction-digits 2;
          }
      }
  }

  deviation /oc-platform:components/oc-platform:component/oc-platform:power-supply/oc-platform:state/oc-platform-psu:input-current {
      deviate replace {
          type decimal64 {
              fraction-digits 2;
          }
      }
  }

  deviation /oc-platform:components/oc-platform:component/oc-platform:power-supply/oc-platform:state/oc-platform-psu:output-current {
      deviate replace {
          type decimal64 {
              fraction-digits 2;
          }
      }
  }

  deviation /oc-platform:components/oc-platform:component/oc-platform:power-supply/oc-platform:state/oc-platform-psu:output-voltage {
      deviate replace {
          type decimal64 {
              fraction-digits 2;
          }
      }
  }

  deviation /oc-platform:components/oc-platform:component/oc-platform:power-supply/oc-platform:state/oc-platform-psu:output-power {
      deviate replace {
          type decimal64 {
              fraction-digits 2;
          }
      }
  }

  deviation /oc-platform:components/oc-platform:component/oc-platform-transceiver:transceiver/oc-platform-transceiver:state/oc-platform-transceiver:date-code {
      deviate replace {
          type string;
      }
  }

  deviation /oc-platform:components/oc-platform:component/oc-platform:state/oc-platform:temperature/oc-platform:avg {
      deviate replace {
          type decimal64 {
              fraction-digits 2;
          }
      }
  }

  deviation /oc-platform:components/oc-platform:component/oc-platform:state/oc-platform:temperature/oc-platform:instant {
      deviate replace {
          type decimal64 {
              fraction-digits 2;
          }
      }
  }

  deviation /oc-platform:components/oc-platform:component/oc-platform:state/oc-platform:temperature/oc-platform:max {
      deviate replace {
          type decimal64 {
              fraction-digits 2;
          }
      }
  }

  deviation /oc-platform:components/oc-platform:component/oc-platform:state/oc-platform:temperature/oc-platform:min {
      deviate replace {
          type decimal64 {
              fraction-digits 2;
          }
      }
  }

  deviation /oc-platform:components/oc-platform:component/oc-platform-transceiver:transceiver/oc-platform-transceiver:physical-channels/oc-platform-transceiver:channel/oc-platform-transceiver:state/oc-platform-transceiver:input-power/oc-platform-transceiver:instant {
      deviate replace {
          type decimal64 {
              fraction-digits 3;
          }
      }
  }

  deviation /oc-platform:components/oc-platform:component/oc-platform-transceiver:transceiver/oc-platform-transceiver:physical-channels/oc-platform-transceiver:channel/oc-platform-transceiver:state/oc-platform-transceiver:output-power/oc-platform-transceiver:instant {
      deviate replace {
          type decimal64 {
              fraction-digits 3;
          }
      }
  }

  deviation /oc-platform:components/oc-platform:component/oc-platform-transceiver:transceiver/oc-platform-transceiver:physical-channels/oc-platform-transceiver:channel/oc-platform-transceiver:state/oc-platform-transceiver:laser-bias-current/oc-platform-transceiver:instant {
      deviate replace {
          type decimal64 {
              fraction-digits 3;
          }
      }
  }

  deviation /oc-platform:components/oc-platform:component/oc-platform-transceiver:transceiver/oc-platform-transceiver:state/oc-platform-transceiver:input-power/oc-platform-transceiver:instant {
      deviate replace {
          type decimal64 {
              fraction-digits 3;
          }
      }
  }

  deviation /oc-platform:components/oc-platform:component/oc-platform-transceiver:transceiver/oc-platform-transceiver:state/oc-platform-transceiver:output-power/oc-platform-transceiver:instant {
      deviate replace {
          type decimal64 {
              fraction-digits 3;
          }
      }
  }

  deviation /oc-platform:components/oc-platform:component/oc-platform-transceiver:transceiver/oc-platform-transceiver:state/oc-platform-transceiver:laser-bias-current/oc-platform-transceiver:instant {
      deviate replace {
          type decimal64 {
              fraction-digits 3;
          }
      }
  }

  deviation	/oc-platform:components/oc-platform:component/oc-platform:backplane {
    deviate not-supported;
  }

  deviation	/oc-platform:components/oc-platform:component/oc-platform:chassis {
    deviate not-supported;
  }

  deviation	/oc-platform:components/oc-platform:component/oc-platform:fabric {
    deviate not-supported;
  }

  deviation	/oc-platform:components/oc-platform:component/oc-platform:integrated-circuit {
    deviate not-supported;
  }

  deviation	/oc-platform:components/oc-platform:component/oc-platform:port/oc-port:breakout-mode {
    deviate not-supported;
  }

  deviation	/oc-platform:components/oc-platform:component/oc-platform:properties {
    deviate not-supported;
  }

  deviation	/oc-platform:components/oc-platform:component/oc-platform:software-module {
    deviate not-supported;
  }

  deviation	/oc-platform:components/oc-platform:component/oc-platform:storage {
    deviate not-supported;
  }
}

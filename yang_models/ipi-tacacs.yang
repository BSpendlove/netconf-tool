/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-tacacs.yang
*
*/

module ipi-tacacs {

    yang-version 1.1;

    namespace   "http://www.ipinfusion.com/yang/ocnos/ipi-tacacs";

    prefix "ipi-tacacs";

    import cml-data-types {
        prefix cml-data-types;
        revision-date 2022-04-04;
    }

    import ipi-tacacs-types {
        prefix ipi-tacacs-types;
        revision-date 2021-09-03;
    }

    import ipi-vrf {
        prefix ipi-vrf;
        revision-date 2021-09-03;
    }

    import ipi-network-instance {
        prefix ipi-network-instance;
        revision-date 2021-11-10;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 tacacs configurations";


    revision "2022-02-16" {
        description "Added changes to make feature enable attribute mandatory";
        reference " 0.3.0.";
    }

    revision "2021-09-03" {
        description "Update descriptions of attribute";
        reference " 0.2.4.";
    }

    revision "2021-05-10" {
        description "Added dependecy on key type for secret key string attribute";
        reference " 0.2.3.";
    }

    revision "2021-04-29" {
        description "Specified CLI input to RDN host address and updated descriptions";
        reference " 0.2.2.";
    }

    revision "2021-04-27" {
        description "Added dependency on sequence number for remote server object list";
        reference " 0.2.1.";
    }

    revision "2021-02-05" {
        description "Restructured module as per open-config style";
        reference " 0.2.0.";
    }

    revision "2018-06-21" {
        description "Initial Version";
        reference " 0.1.0.";
    }

    grouping tacacs-global-key-config {
        description
            "TACACS Configuration items for KEYS";
        leaf key-type  {
            type  ipi-tacacs-types:tacacs_hostp_key_type_t;
            description "Authentication key value";
        } // END of key-type definition.

        leaf secret-key-string  {
            when " /ipi-tacacs:tacacs/ipi-tacacs:vrf/ipi-tacacs:config/ipi-tacacs:key-type ";
            type  string {
                length "1..1965";
                pattern "[^?' =,>|]+";
            }
            description "Shared key used between the authentication-server and the device";
        } // END of secret-key-string definition.

    } // END of tacacs-global-key-config definition.
    grouping tacacs-counter-state {
        description
            "State items for TACACS notification";
    } // END of tacacs-counter-state definition.
    grouping tacacs-global-config {
        description
            "TACACS Global Configuration items";
        leaf vrf-name  {
            type  leafref {
                path  "/ipi-network-instance:network-instances/ipi-network-instance:network-instance/ipi-vrf:vrf/ipi-vrf:config/ipi-vrf:vrf-name";
            }
            description "VRF Name associated with this instance";
        } // END of vrf-name definition.

        leaf feature-enable  {
            type  empty;
            mandatory true;
            description "Use this attribute to enable the TACACS+ feature";
        } // END of feature-enable definition.

        leaf timeout  {
            type  uint8 {
                 range "1..60"  {
                    description "1..60:TACACS+ server timeout period in seconds";
                 }
            }
            description "Use this attribute to set the period to wait for a response from the
                        server before the client declares a
                        timeout failure. The default timeout value is 5 seconds.";
        } // END of timeout definition.

    } // END of tacacs-global-config definition.
    grouping tacacs-server-key-config {
        description
            "TACACS Configuration items for KEYS in Servers";
        leaf key-type  {
            type  ipi-tacacs-types:tacacs_hostp_key_type_t;
            description "Authentication key value";
        } // END of key-type definition.

        leaf secret-key-string  {
            when " /ipi-tacacs:tacacs/ipi-tacacs:vrf/ipi-tacacs:remote-servers/ipi-tacacs:server/ipi-tacacs:config/ipi-tacacs:key-type ";
            type  string {
                length "1..1965";
                pattern "[^?' =,>|]+";
            }
            description "Shared key used between the authentication-server and the device";
        } // END of secret-key-string definition.

    } // END of tacacs-server-key-config definition.
    grouping tacacs-server-config {
        description
            "TACACS Server Configuration items";
        leaf host-address  {
            type  cml-data-types:cml_hostname_t;
            description "Use this attribute to set the TACACS+ server host name or IP address.";
        } // END of host-address definition.

        leaf sequence-number  {
            type  uint8 {
                 range "1..8"  {
                    description "1..8:sequence number for servers";
                 }
            }
            mandatory true;
            description "Use this attribute to set the sequence-number/priority index for the
                        TACACS+ server";
        } // END of sequence-number definition.

        leaf port  {
            type  uint32 {
                 range "1025..65535"  {
                    description "1025..65535:TACACS+ server port";
                 }
            }
            description "Port number used for TACACS+ Server Connection";
        } // END of port definition.

        leaf timeout  {
            type  uint32 {
                 range "1..60"  {
                    description "1..60:TACACS+ server timeout period in seconds";
                 }
            }
            description "To represent the timeout configured by the user";
        } // END of timeout definition.

    } // END of tacacs-server-config definition.
    grouping tacacs-debug-config {
        description
            "Configuration data related to debugging";
        leaf tacacs-debug  {
            type  empty;
            description "This attribute is to enable/disable TACACS+ debug logging";
        } // END of tacacs-debug definition.

    } // END of tacacs-debug-config definition.

    grouping  tacacs-grouping {
    description
        "TACACS related operation";
    container tacacs {
        description
            "TACACS related operation";

        list vrf {
            if-feature feature-list:HAVE_HOSTPD;
            if-feature feature-list:HAVE_AAA;
            if-feature feature-list:HAVE_TACACS_CLIENT;
            key "vrf-name";
            description
                "Global TACACS Server Configuration";
            leaf vrf-name  {
                type  leafref {
                    path  "../config/vrf-name";
                }
                description "VRF Name associated with this instance";
            } // END of vrf-name definition.

            container config {
                description
                    "tacacs related operation";
                uses tacacs-global-config;
                uses tacacs-global-key-config;
            } // END of config-container definition.
            container state {
                config false;
                description
                    "This container defines the TACACS Global states.";
                uses tacacs-global-config;
                uses tacacs-global-key-config;
            } // END of state-container definition.
            container remote-servers {
                description
                    "This container defines tacacs server informations";

                list server {
                when " /ipi-tacacs:tacacs/ipi-tacacs:vrf/ipi-tacacs:remote-servers/ipi-tacacs:server/ipi-tacacs:config/ipi-tacacs:sequence-number ";
                    if-feature feature-list:HAVE_HOSTPD;
                    if-feature feature-list:HAVE_AAA;
                    if-feature feature-list:HAVE_TACACS_CLIENT;
                    key "host-address";
                    description
                        "This objectlist defines the TACACS server list";
                    leaf host-address  {
                        type  leafref {
                            path  "../config/host-address";
                        }
                        description "Use this attribute to set the TACACS+ server host name or IP address";
                    } // END of host-address definition.

                    container config {
                        description
                            "This container defines TACACS server operation";
                        uses tacacs-server-config;
                        uses tacacs-server-key-config;
                    } // END of config-container definition.
                    container state {
                        config false;
                        description
                            "This container defines TACACS Server state intormation.";
                        uses tacacs-server-config;
                        uses tacacs-server-key-config;
                        uses tacacs-counter-state;
                    } // END of state-container definition.
                } // End of server-list
            } // END of remote-servers-container definition.
        } // End of vrf-list
        container debug {
            description
                "TACACS debug";
            container config {
                description
                    "This container defines TACACS Debug Configuration";
                uses tacacs-debug-config;
            } // END of config-container definition.
            container state {
                config false;
                description
                    "This container defines TACACS Debug state";
                uses tacacs-debug-config;
            } // END of state-container definition.
        } // END of debug-container definition.
    } // END of tacacs-container definition.
    } // END of tacacs-grouping definition.

    uses tacacs-grouping;

    rpc clear-all-tacacs-server-counters {
        description "Use this RPC to clear all tacacs-server counters";
        input  {
            leaf vrf-name  {
                type string;
                mandatory true;
                description "VRF Name associated with this instance";
            }
        }
    }

    rpc clear-tacacs-server-host-counters {
        description "Use this RPC to clear counters for a TACACS server by hostname or IP
                    address";
        input  {
            leaf hostname  {
                type cml-data-types:cml_hostpname_t;
                mandatory true;
                description "Use this attribute to set the TACACS+ server host name or IP address";
            }
            leaf vrf-name  {
                type string;
                mandatory true;
                description "VRF Name associated with this instance";
            }
        }
    }

    rpc tacacs-terminal-debugging-on {
        description "Use this RPC to turn on TACACS terminal debug logs";
        input  {
            leaf debug-options  {
                type empty;
                mandatory true;
                description "To display TACACS+ debugging information.";
            }
        }
    }

    rpc tacacs-terminal-debugging-off {
        description "Use this RPC to turn off TACACS terminal debug logs";
        input  {
            leaf debug-options  {
                type empty;
                mandatory true;
                description "To display TACACS+ debugging information.";
            }
        }
    }

}

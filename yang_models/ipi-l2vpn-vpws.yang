/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-l2vpn-vpws.yang
*
*/

module ipi-l2vpn-vpws {

    yang-version 1.1;

    namespace   "http://www.ipinfusion.com/yang/ocnos/ipi-l2vpn-vpws";

    prefix "ipi-l2vpn-vpws";

    import cml-data-types {
        prefix cml-data-types;
        revision-date 2022-04-04;
    }

    import ipi-interface {
        prefix ipi-interface;
        revision-date 2022-04-05;
    }

    import ipi-network-instance-types {
        prefix ipi-network-instance-types;
        revision-date 2021-11-10;
    }

    import ipi-network-instance {
        prefix ipi-network-instance;
        revision-date 2021-11-10;
    }

    import ipi-mpls {
        prefix ipi-mpls;
        revision-date 2022-04-22;
    }

    import ipi-vpws-types {
        prefix ipi-vpws-types;
        revision-date 2021-09-03;
    }

    import ipi-qos {
        prefix ipi-qos;
        revision-date 2022-01-13;
    }

    import ietf-inet-types {
        prefix inet;
        revision-date 2013-07-15;
    }

    import ietf-yang-types {
        prefix yang;
        revision-date 2013-07-15;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for VPWS pseudowire";


    revision "2021-12-08" {
        description "Added if-not-feature flag for DC-MPLS for queue-to-cos-profile";
        reference "Initial Version";
    }

    revision "2021-11-16" {
        description "Adding L2CP support";
        reference "Initial Version";
    }

    revision "2021-09-06" {
        description "Removing the dependency of L2VPN VPWS configuration in subinterface with global L2VPN VPWS configurataion";
        reference "Initial Version";
    }

    revision "2021-09-01" {
        description "Changed base interface module's switchport attribute name and the datatype from bool to empty";
        reference "Initial Version";
    }

    revision "2021-08-24" {
        description "Updated dependency for VPWS interface on svc template name";
        reference "Initial Version";
    }

    revision "2021-08-03" {
        description "Added L2VPN VPWS attributes for Sub-interface";
        reference "Initial Version";
    }

    revision "2021-07-15" {
        description "Added attributes related to VCCV and additional constraints for tunnel attributes ";
        reference "Initial Version";
    }

    revision "2021-04-27" {
        description "service-template is constrained with string length";
        reference "Initial Version";
    }

    revision "2021-03-10" {
        description "pw-link-mode made mandatory to support Secondary pw-mode config";
        reference "Initial Version";
    }

    revision "2020-11-25" {
        description "Initial Version";
        reference "Initial Version";
    }

    grouping vpws-pseudowire-config {
        description
            "Top level Grouping for Fec128 pseudowire";
        leaf pseudowire-identifier  {
            type  uint32 {
                 range "1..4294967295"  {
                    description "1..4294967295:Identifying value used for MPLS Layer-2 Virtual Circuit";
                 }
            }
            description "Use this attribute to assign pseudowire identifier to create an
                        instance of an MPLS layer 2 virtual circuit.";
        } // END of pseudowire-identifier definition.

        leaf peer-address  {
            type  ipi-vpws-types:vpws_ip_addr_t;
            description "Use this attribute to specify pseudowire end peer IP address to create
                        an instance of an MPLS layer 2 virtual circuit";
        } // END of peer-address definition.

    } // END of vpws-pseudowire-config definition.
    grouping vpws-pseudowire-service-tpid-config {
        description
            "Grouping for Service TPID pseudowire";
        leaf service-tpid  {
            when " not(/ipi-network-instance:network-instances/ipi-network-instance:network-instance/ipi-l2vpn-vpws:vpws-instance/ipi-l2vpn-vpws:pseudowire/ipi-l2vpn-vpws:raw/ipi-l2vpn-vpws:config/ipi-l2vpn-vpws:enable-raw-mode) + not(/ipi-network-instance:network-instances/ipi-network-instance:network-instance/ipi-l2vpn-vpws:vpws-instance/ipi-l2vpn-vpws:pseudowire/ipi-l2vpn-vpws:tagged/ipi-l2vpn-vpws:config/ipi-l2vpn-vpws:enable-tagged-mode) ";
            type  ipi-vpws-types:vpws_svc_tpid_t;
            description "Use this attribute to specify tunneling ethertype to be used for an
                        instance of an MPLS layer 2 virtual circuit";
        } // END of service-tpid definition.

    } // END of vpws-pseudowire-service-tpid-config definition.
    grouping vpws-pseudowire-fec129-config {
        description
            "Top level Grouping for Fec129 pseudowire";
        leaf peer-address  {
            type  inet:ipv4-address;
            description "Use this attribute to specify pseudowire end peer IP address to create
                        an instance of an MPLS layer 2 virtual circuit";
        } // END of peer-address definition.

        leaf attachment-group-identifier  {
            type  string {
                length "1..1965";
                pattern "[^?' =,>|]+";
            }
            description "Use this attribute to specify AGI value for genfec pseudowire";
        } // END of attachment-group-identifier definition.

        leaf source-attachment-individual-identifier  {
            type  string {
                length "1..4";
                pattern "[^?' =,>|]+";
            }
            description "Use this attribute to specify SAII value for genfec pseudowire";
        } // END of source-attachment-individual-identifier definition.

        leaf target-attachment-individual-identifier  {
            type  string {
                length "1..4";
                pattern "[^?' =,>|]+";
            }
            description "Use this attribute to specify TAII value for genfec pseudowire";
        } // END of target-attachment-individual-identifier definition.

    } // END of vpws-pseudowire-fec129-config definition.
    grouping vpws-pseudowire-common-config {
        description
            "Grouping for common attributes of  pseudowire";
        leaf group-name  {
            type  string {
                length "1..32";
                pattern "[^?' =,>|]+";
            }
            description "Use this attribute to create a group name with default available
                        group-identifier for MPLS Layer-2 Virtual Circuit.";
        } // END of group-name definition.

        leaf group-identifier  {
            when " ../group-name ";
            type  uint32 {
                 range "1..4294967295"  {
                    description "1..4294967295:Identifier for the group (group-id to be used in LDP)";
                 }
            }
            description "Use this attribute to create a group with specific group-identifier
                        for MPLS Layer-2 Virtual Circuit.";
        } // END of group-identifier definition.

        leaf enable-control-word  {
            type  empty;
            description "Use this attribute to enable control word for MPLS Layer-2 Virtual
                        Circuit.";
        } // END of enable-control-word definition.

        leaf tunnel-name  {
            when " not(../tunnel-identifier) + not(../tunnel-policy) ";
            type  string {
                length "1..32";
                pattern "[^?' =,>|]+";
            }
            description "Use this attribute to specificy the transport tunnel-name to be used
                        for MPLS Layer-2 Virtual Circuit.";
        } // END of tunnel-name definition.

        leaf tunnel-policy  {
            when " not(../tunnel-identifier) + not(../tunnel-name) ";
            if-feature feature-list:HAVE_MPLS_SERVICE_MAPPING;
            type  string {
                length "1..127";
                pattern "[^?' =,>|]+";
            }
            description "Use this attribute to specificy transport tunnel-policy to be used for
                        MPLS Layer-2 Virtual Circuit.";
        } // END of tunnel-policy definition.

        leaf tunnel-identifier  {
            when " not(../tunnel-name) + not(../tunnel-policy) ";
            type  uint32 {
                 range "1..5000"  {
                    description "1..5000:Identifying value for Tunnel-id";
                 }
            }
            description "Use this attribute to specificy the static tunnel-identifier to be
                        used for MPLS Layer-2 Virtual Circuit.";
        } // END of tunnel-identifier definition.

        leaf allow-l2protocol-peer  {
            if-feature feature-list:HAVE_CUSTOM1_MPLS;
            type  empty;
            description "Use this attribute to configure L2CP in peer mode";
        } // END of allow-l2protocol-peer definition.

    } // END of vpws-pseudowire-common-config definition.
    grouping vpws-pseudowire-default-tagged-config {
        description
            "Grouping for default tagged pseudowire attributes";
        leaf enable-default-tagged-mode  {
            type  empty;
            mandatory true;
            description "This attribute is used to enable default-tagged mode of pseudowire.
                        This can be enabled at creation time";
        } // END of enable-default-tagged-mode definition.

    } // END of vpws-pseudowire-default-tagged-config definition.
    grouping vpws-pseudowire-tagged-config {
        description
            "Grouping for tagged pseudowire attributes";
        leaf enable-tagged-mode  {
            type  empty;
            mandatory true;
            description "This attribute is used to enable tagged mode of pseudowire. This can
                        be enabled at creation time";
        } // END of enable-tagged-mode definition.

    } // END of vpws-pseudowire-tagged-config definition.
    grouping vpws-pseudowire-raw-config {
        description
            "Grouping for raw pseudowire attributes";
        leaf enable-raw-mode  {
            type  empty;
            mandatory true;
            description "This attribute is used to enable raw mode of pseudowire. This can be
                        enabled at creation time";
        } // END of enable-raw-mode definition.

    } // END of vpws-pseudowire-raw-config definition.
    grouping vpws-pseudowire-static-config {
        description
            "Grouping for static pw attributes";
        leaf enable-manual-pseudowire  {
            type  empty;
            description "This attribute is used to configure static pseudowire.";
        } // END of enable-manual-pseudowire definition.

    } // END of vpws-pseudowire-static-config definition.
    grouping vpws-pseudowire-vccv-config {
        description
            "Grouping for vccv attributes for PW";
        leaf control-channel-type  {
            if-feature feature-list:HAVE_VCCV;
            if-feature feature-list:HAVE_CUSTOM1_MPLS_BFD;
            type  ipi-vpws-types:vpws_mpls_vccv_cc_type_t;
            description "Use this attribute to configure the Control-Channel type for VCCV";
        } // END of control-channel-type definition.

        leaf control-verification-type  {
            if-feature feature-list:HAVE_VCCV;
            if-feature feature-list:HAVE_CUSTOM1_MPLS_BFD;
            type  ipi-vpws-types:vpws_mpls_vccv_cv_type_t;
            description "Use this attribute to configure the Control-Verification supported by
                        BFD for VCCV";
        } // END of control-verification-type definition.

    } // END of vpws-pseudowire-vccv-config definition.
    grouping vpws-pseudowire-mplstp-config {
        description
            "Grouping for MPLS-TP attributes for PW";
    } // END of vpws-pseudowire-mplstp-config definition.
    grouping vpws-interface-config {
        description
            "Grouping for Interface config attribute";
        leaf name  {
            type  leafref {
                path  "/ipi-interface:interfaces/ipi-interface:interface/ipi-interface:name";
            }
            description "This attribute describes the interface on which attachment circuit is
                        to be created for  pseudowire.";
        } // END of name definition.

    } // END of vpws-interface-config definition.
    grouping l2vpn-vpws-top {
        description
            "Top level grouping for L2VPN VPWS configuration";
        container vpws-access {
            when " /ipi-l2vpn-vpws:vpws/ipi-l2vpn-vpws:interfaces/ipi-l2vpn-vpws:interface/ipi-l2vpn-vpws:vpws-access/ipi-l2vpn-vpws:config/ipi-l2vpn-vpws:enable ";
            if-feature feature-list:HAVE_SUBINTERFACE;
            description
                "Container for L2VPN VPWS data";
            container config {
                presence "yes";
                description
                    "Configuration data for L2VPN VPWS";
                uses l2vpn-vpws-config;
            } // END of config-container definition.
            container state {
                config false;
                description
                    "Operational state data for L2VPN VPWS";
                uses l2vpn-vpws-config;
            } // END of state-container definition.
            container bindings {
                description
                    "Container for L2VPN VPWS binding";

                list binding {
                    key "vpws-name";
                    description
                        "VPWS binding related configuration";
                    leaf vpws-name  {
                        type  leafref {
                            path  "../config/vpws-name";
                        }
                        description "This attribute uniquely identifies a VPWS service on Subinterface";
                    } // END of vpws-name definition.

                    container config {
                        description
                            "Configuration data for L2VPN VPWS binding";
                        uses l2vpn-vpws-bind-config;
                    } // END of config-container definition.
                    container state {
                        config false;
                        description
                            "Operational state data for L2VPN VPWS binding";
                        uses l2vpn-vpws-bind-config;
                    } // END of state-container definition.
                } // End of binding-list
            } // END of bindings-container definition.
        } // END of vpws-access-container definition.
    } // END of l2vpn-vpws-top definition.
    grouping l2vpn-vpws-config {
        description
            "Grouping for L2VPN VPWS service configurations";
        leaf enable  {
            type  empty;
            mandatory true;
            description "This attribute is used to enable VPWS service on Subinterface";
        } // END of enable definition.

        leaf enable-revertive-mode  {
            type  empty;
            description "This attribute is used to configure vc-mode revertive on the interface";
        } // END of enable-revertive-mode definition.

    } // END of l2vpn-vpws-config definition.
    grouping l2vpn-vpws-bind-config {
        description
            "Grouping for L2VPN VPWS bind configuration";
        leaf vpws-name  {
            type  string {
                length "1..30";
                pattern "[^?' =,>|]+";
            }
            description "This attribute uniquely identifies a VPWS service on Subinterface";
        } // END of vpws-name definition.

        leaf pseudowire-link-mode  {
            type  ipi-vpws-types:vpws_mpls_vclinkmode_t;
            mandatory true;
            description "This attribute is used to configure link mode as primary/secondary on
                        VPWS service. Default value is 0";
        } // END of pseudowire-link-mode definition.

    } // END of l2vpn-vpws-bind-config definition.
    grouping vpws-interface-top {
        description
            "Top level grouping for interface level configuration for PW";
        container interfaces {
            description
                "Top level container for interface level configuration for VPWS";

            list interface {
            when " /ipi-l2vpn-vpws:vpws/ipi-l2vpn-vpws:interfaces/ipi-l2vpn-vpws:interface/ipi-l2vpn-vpws:service-template-mapping/ipi-l2vpn-vpws:pseudowire-name  or /ipi-l2vpn-vpws:vpws/ipi-l2vpn-vpws:interfaces/ipi-l2vpn-vpws:interface/ipi-l2vpn-vpws:vpws-access/ipi-l2vpn-vpws:config/ipi-l2vpn-vpws:enable ";
                key "name";
                description
                    "VPWS interface related configuration";
                leaf name  {
                    type  leafref {
                        path  "../config/name";
                    }
                    description "This attribute describes the interface on which attachment circuit is
                                to be created for  pseudowire.";
                } // END of name definition.


                list pseudowire-mode {
                when " ../service-template-mapping ";
                    key "service-template";
                    description
                        "VPWS interface mode related configuration";
                    leaf service-template  {
                        type  leafref {
                            path  "../config/service-template";
                        }
                        description "This attribute is used to configure service-template for vc-mode";
                    } // END of service-template definition.

                    container config {
                        description
                            "Configuration data";
                        uses vpws-interface-global-config;
                    } // END of config-container definition.
                    container state {
                        config false;
                        description
                            "Container for Operational attributes";
                        uses vpws-interface-global-config;
                    } // END of state-container definition.
                } // End of pseudowire-mode-list
                container config {
                    when " /ipi-l2vpn-vpws:vpws/ipi-l2vpn-vpws:interfaces/ipi-l2vpn-vpws:interface/ipi-l2vpn-vpws:service-template-mapping/ipi-l2vpn-vpws:pseudowire-name  or /ipi-l2vpn-vpws:vpws/ipi-l2vpn-vpws:interfaces/ipi-l2vpn-vpws:interface/ipi-l2vpn-vpws:vpws-access/ipi-l2vpn-vpws:config/ipi-l2vpn-vpws:enable ";
                    description
                        "Configuration container for interface list";
                    uses vpws-interface-config;
                } // END of config-container definition.
                container state {
                    config false;
                    description
                        "Operation container for interface list";
                    uses vpws-interface-config;
                } // END of state-container definition.
                uses l2vpn-vpws-top;
                uses vpws-service-template-mapping-top;
            } // End of interface-list
        } // END of interfaces-container definition.
    } // END of vpws-interface-top definition.
    grouping vpws-interface-global-config {
        description
            "Grouping for global interface level configuration for PW";
        leaf service-template  {
            type  string {
                length "1..1965";
                pattern "[^?' =,>|]+";
            }
            description "This attribute is used to configure service-template for vc-mode";
        } // END of service-template definition.

        leaf mode  {
            type  ipi-vpws-types:vpws_mpls_vcmode_t;
            mandatory true;
            description "This attribute is used to configure vc-mode revertive or standy on the
                        interface on which attachment circuit is created for pseudowire.";
        } // END of mode definition.

    } // END of vpws-interface-global-config definition.
    grouping vpws-service-template-mapping-top {
        description
            "Top level grouping for service-template mapping configuration for VPWS";

        list service-template-mapping {
        when " /ipi-interface:interfaces/ipi-interface:interface/ipi-interface:config/ipi-interface:enable-switchport ";
            key "pseudowire-name";
            description
                "List for VPWS mapping to service-template-mapping on interface";
            leaf pseudowire-name  {
                type  leafref {
                    path  "../config/pseudowire-name";
                }
                description "";
            } // END of pseudowire-name definition.

            container config {
                description
                    "Configuration data";
                uses vpws-service-template-mapping-config;
            } // END of config-container definition.
            container state {
                config false;
                description
                    "Container for Operational attributes";
                uses vpws-service-template-mapping-config;
            } // END of state-container definition.
        } // End of service-template-mapping-list
    } // END of vpws-service-template-mapping-top definition.
    grouping vpws-service-template-mapping-config {
        description
            "Grouping for service-template mapping configurationattributes for VPWS";
        leaf pseudowire-name  {
            type  string {
                length "1..1965";
                pattern "[^?' =,>|]+";
            }
            description "This attribute is used to map pseudowire on customer interface for
                        attachment circuit";
        } // END of pseudowire-name definition.

        leaf service-template-name  {
            type  leafref {
                path  "/ipi-mpls:mpls/ipi-mpls:l2vpn/ipi-mpls:customer-service-template/ipi-mpls:name";
            }
            mandatory true;
            description "This attribute is used to map service-template on customer interface
                        for attachment circuit";
        } // END of service-template-name definition.

        leaf pseudowire-link-mode  {
            type  ipi-vpws-types:vpws_mpls_vclinkmode_t;
            mandatory true;
            description "This attribute is used to configure link mode as primary/secondary on
                        customer interface for attachment circuit";
        } // END of pseudowire-link-mode definition.

        leaf cos-to-queue-profile-name  {
            when " /ipi-qos:qos/ipi-qos:global/ipi-qos:map-profile/ipi-qos:cos-to-queue-profiles/ipi-qos:cos-to-queue-profile/ipi-qos:name ";
            if-feature feature-list:HAVE_QOS_MAPPING_PROFILE;
            type  string {
                length "1..1965";
                pattern "[^?' =,>|]+";
            }
            description "This attribute is used to map cos-to-queue profile on customer
                        interface for attahment circuit";
        } // END of cos-to-queue-profile-name definition.

        leaf queue-to-cos-profile-name  {
            when " /ipi-qos:qos/ipi-qos:global/ipi-qos:map-profile/ipi-qos:queue-color-to-cos-profiles/ipi-qos:queue-color-to-cos-profile/ipi-qos:name ";
            if-feature feature-list:HAVE_QOS_MAPPING_PROFILE;
            if-feature feature-list:NOT_HAVE_CUSTOM1_MPLS;
            type  string {
                length "1..1965";
                pattern "[^?' =,>|]+";
            }
            description "This attribute is used to map queue-to-cos profile on customer
                        interface for attahment circuit";
        } // END of queue-to-cos-profile-name definition.

    } // END of vpws-service-template-mapping-config definition.
    grouping vpws-static-forwarding-top {
        description
            "Top level grouping for static FIB configuration for VPWS";
        container static-forwarding {
            description
                "Top level container for Static VPWS FIB configuration";

            list forwarding-information-base {
            when " /ipi-network-instance:network-instances/ipi-network-instance:network-instance/ipi-l2vpn-vpws:vpws-instance/ipi-l2vpn-vpws:pseudowire/ipi-l2vpn-vpws:default-tagged/ipi-l2vpn-vpws:config/ipi-l2vpn-vpws:enable-manual-pseudowire  or /ipi-network-instance:network-instances/ipi-network-instance:network-instance/ipi-l2vpn-vpws:vpws-instance/ipi-l2vpn-vpws:pseudowire/ipi-l2vpn-vpws:tagged/ipi-l2vpn-vpws:config/ipi-l2vpn-vpws:enable-manual-pseudowire  or /ipi-network-instance:network-instances/ipi-network-instance:network-instance/ipi-l2vpn-vpws:vpws-instance/ipi-l2vpn-vpws:pseudowire/ipi-l2vpn-vpws:raw/ipi-l2vpn-vpws:config/ipi-l2vpn-vpws:enable-manual-pseudowire ";
            // when " ../forwarding-information-base/config/access-interface-name ";
                key "pseudowire-identifier";
                description
                    "VPWS FIB configuration list";
                leaf pseudowire-identifier  {
                    type  leafref {
                        path  "../config/pseudowire-identifier";
                    }
                    description "";
                } // END of pseudowire-identifier definition.

                container config {
                    description
                        "Configuration data";
                    uses vpws-forwarding-information-base-config;
                } // END of config-container definition.
                container state {
                    config false;
                    description
                        "Container for Operational attributes";
                    uses vpws-forwarding-information-base-config;
                } // END of state-container definition.
            } // End of forwarding-information-base-list
        } // END of static-forwarding-container definition.
    } // END of vpws-static-forwarding-top definition.
    grouping vpws-forwarding-information-base-config {
        description
            "Grouping for static FIB configuration for VPWS";
        leaf pseudowire-identifier  {
            type  leafref {
                path  "/ipi-network-instance:network-instances/ipi-network-instance:network-instance/vpws-instance/pseudowire/config/pseudowire-identifier";
            }
            description "This attribute is used to map static pseudowire identifier for
                        creating static VC fib entry";
        } // END of pseudowire-identifier definition.

        leaf incoming-label  {
            type  uint32 {
                 range "16..15999"  {
                    description "16..15999:in-coming Label <16-15999>";
                 }
            }
            mandatory true;
            description "This attribute is used to configure in-label for static VC fib entry";
        } // END of incoming-label definition.

        leaf outgoing-label  {
            type  uint32 {
                 range "16..15999"  {
                    description "16..15999:Out-going Label <16-15999>";
                 }
            }
            mandatory true;
            description "This attribute is used to configure out-label for static VC fib entry";
        } // END of outgoing-label definition.

        leaf nexthop-address  {
            type  inet:ip-address;
            mandatory true;
            description "This attribute is used to configure VC next-hop address for static VC
                        fib entry";
        } // END of nexthop-address definition.

        leaf provider-interface-name  {
            type  leafref {
                path  "/ipi-interface:interfaces/ipi-interface:interface/ipi-interface:name";
            }
            mandatory true;
            description "This attribute is used to configure provider network interface for
                        static VC fib entry";
        } // END of provider-interface-name definition.

        leaf access-interface-name  {
            type  leafref {
                path  "/vpws/interfaces/interface/name";
            }
            mandatory true;
            description "This attribute is used to configure customer network interface for
                        static VC fib entry";
        } // END of access-interface-name definition.

    } // END of vpws-forwarding-information-base-config definition.
    grouping vpws-state-global-counters {
        description
            "Grouping for runtime counters attributes";
        leaf total-pseudowires  {
            type  uint32;
            config false;
            description "This attribute provides total number of pseudowires created";
        } // END of total-pseudowires definition.

        leaf active-pseudowires  {
            type  uint32;
            config false;
            description "This attribute provides total number of pseudowires active";
        } // END of active-pseudowires definition.

        leaf inactive-pseudowires  {
            type  uint32;
            config false;
            description "This attribute provides total number of pseudowires inactive";
        } // END of inactive-pseudowires definition.

        leaf oam-pseudowires  {
            type  uint32;
            config false;
            description "This attribute provides total number of oam pseudowires";
        } // END of oam-pseudowires definition.

    } // END of vpws-state-global-counters definition.
    grouping vpws-global-state-top {
        description
            "Top level grouping for runtime data for VPWS";
        container global {
            config false;
            description
                "Top level container for global state data";
            container state {
                config false;
                description
                    "State container for global state data";
                container counters {
                    config false;
                    description
                        "Container for VPWS counters data";
                    uses vpws-state-global-counters;
                } // END of counters-container definition.
            } // END of state-container definition.
        } // END of global-container definition.
    } // END of vpws-global-state-top definition.
    grouping vpws-pseudowire-state {
        description
            "Grouping for runtime attributes for pseudowire";
        leaf vc-admin-status  {
            if-feature feature-list:HAVE_UNI_CLI;
            type  ipi-vpws-types:vpws_mpls_vc_admin_status_t;
            config false;
            description "This attribute provides admin-status of pseudowire";
        } // END of vc-admin-status definition.

        leaf up-time  {
            type  yang:date-and-time {
                pattern "\\d{4}-\\d{2}-\\d{2}T\\d{2}:\\d{2}:\\d{2}(\\.\\d+)?(Z|[\\+\\-]\\d{2}:\\d{2})";
                }
                config false;
                description "This attribute provides time when pseudowire comes to forwarding state";
            } // END of up-time definition.

            leaf last-change-time  {
                type  yang:date-and-time {
                    pattern "\\d{4}-\\d{2}-\\d{2}T\\d{2}:\\d{2}:\\d{2}(\\.\\d+)?(Z|[\\+\\-]\\d{2}:\\d{2})";
                    }
                    config false;
                    description "This attribute provides time when pseudowire changes its last state";
                } // END of last-change-time definition.

                leaf create-time  {
                    type  yang:date-and-time {
                        pattern "\\d{4}-\\d{2}-\\d{2}T\\d{2}:\\d{2}:\\d{2}(\\.\\d+)?(Z|[\\+\\-]\\d{2}:\\d{2})";
                        }
                        config false;
                        description "This attribute provides time when pseudowire was created";
                    } // END of create-time definition.

                    leaf owner  {
                        type  ipi-vpws-types:vpws_mpls_vc_owner_t;
                        config false;
                        description "This attribute provides owner name of pseudowire";
                    } // END of owner definition.

                    leaf non-te-mapping-direction  {
                        type  ipi-vpws-types:vpws_mpls_mapping_dir_t;
                        config false;
                        description "This attribute provides mapping direction of pseudowire";
                    } // END of non-te-mapping-direction definition.

                    leaf remote-pseudowire-status  {
                        type  ipi-vpws-types:vpws_mpls_pw_status_t;
                        config false;
                        description "This attribute provides pseudowire status of the peer end node";
                    } // END of remote-pseudowire-status definition.

                    leaf pseudowire-state  {
                        type  ipi-vpws-types:vpws_mpls_pw_state_t;
                        config false;
                        description "This attribute provides local pseudowire state";
                    } // END of pseudowire-state definition.

                    leaf pseudowire-index  {
                        type  uint32;
                        config false;
                        description "This attribute provides pseudowire index";
                    } // END of pseudowire-index definition.

                    leaf pseudowire-type  {
                        type  ipi-vpws-types:vpws_mpls_pw_type_t;
                        config false;
                        description "This attribute provides type of pseudowire information";
                    } // END of pseudowire-type definition.

                    leaf pseudowire-mode  {
                        type  ipi-vpws-types:vpws_mpls_pw_mode_t;
                        config false;
                        description "This attribute provides mode of pseudowire information";
                    } // END of pseudowire-mode definition.

                    leaf pseudowire-label  {
                        type  uint32;
                        config false;
                        description "This attribute provides pseudowire out label information";
                    } // END of pseudowire-label definition.

                    leaf tunnel-label  {
                        type  uint32;
                        config false;
                        description "This attribute provides tunnel label information";
                    } // END of tunnel-label definition.

                    leaf network-interface-name  {
                        type  string {
                            length "1..1965";
                            pattern "[^?' =,>|]+";
                        }
                        config false;
                        description "This attribute provides network provider interface name for the
                                    pseudowire";
                    } // END of network-interface-name definition.

                    leaf customer-service-template-name  {
                        type  string {
                            length "1..1965";
                            pattern "[^?' =,>|]+";
                        }
                        config false;
                        description "This attribute provides service template name mapping on this
                                    pseudowire";
                    } // END of customer-service-template-name definition.

    } // END of vpws-pseudowire-state definition.

    grouping  vpws-instance-grouping {
    description
        "Top level container for vpws instance";
    container vpws-instance {
        description
            "Top level container for vpws instance";

        list pseudowire {
        // when " ipi-l2vpn-vpws:vpws-instance/pseudowire/raw/config/enable-raw-mode || ipi-l2vpn-vpws:vpws-instance/pseudowire/tagged/config/enable-tagged-mode || ipi-l2vpn-vpws:vpws-instance/pseudowire/default-tagged/config/enable-default-tagged-mode ";
            key "pseudowire-identifier peer-address";
            max-elements 1;
            description
                "Object list for Fec-128 pseudowire";
            leaf pseudowire-identifier  {
                type  leafref {
                    path  "../config/pseudowire-identifier";
                }
                description "Use this attribute to assign pseudowire identifier to create an
                            instance of an MPLS layer 2 virtual circuit. A Layer-2 MPLS Virtual
                            Circuit instance may be bound to any interface on the router; however,
                            only one interface may be bound to a Layer-2 circuit at a time.";
            } // END of pseudowire-identifier definition.

            leaf peer-address  {
                type  leafref {
                    path  "../config/peer-address";
                }
                description "Use this attribute to specify pseudowire end peer IP address to create
                            an instance of an MPLS layer 2 virtual circuit";
            } // END of peer-address definition.

            container config {
                description
                    "Top level configuration data for Fec128 pseudowire";
                uses vpws-pseudowire-config;
            } // END of config-container definition.
            container state {
                config false;
                description
                    "Container for Operational attributes for pseudowire";
                uses vpws-pseudowire-config;
                uses vpws-pseudowire-state;
            } // END of state-container definition.
            container default-tagged {
                when " not(/ipi-network-instance:network-instances/ipi-network-instance:network-instance/ipi-l2vpn-vpws:vpws-instance/ipi-l2vpn-vpws:pseudowire/ipi-l2vpn-vpws:raw/ipi-l2vpn-vpws:config/ipi-l2vpn-vpws:enable-raw-mode) + not(/ipi-network-instance:network-instances/ipi-network-instance:network-instance/ipi-l2vpn-vpws:vpws-instance/ipi-l2vpn-vpws:pseudowire/ipi-l2vpn-vpws:tagged/ipi-l2vpn-vpws:config/ipi-l2vpn-vpws:enable-tagged-mode) ";
                description
                    "Default Tagged container for Fec128 pseudowire";
                container config {
                    presence "Create Default-Tagged VPWS Fec-128 Instance";
                    description
                        "Top level configuration data for Fec128 pseudowire";
                    uses vpws-pseudowire-common-config;
                    uses vpws-pseudowire-default-tagged-config;
                    uses vpws-pseudowire-mplstp-config;
                    uses vpws-pseudowire-service-tpid-config;
                    uses vpws-pseudowire-static-config;
                    uses vpws-pseudowire-vccv-config;
                } // END of config-container definition.
                container state {
                    config false;
                    description
                        "Container for Operational attributes for pseudowire";
                    uses vpws-pseudowire-common-config;
                    uses vpws-pseudowire-default-tagged-config;
                    uses vpws-pseudowire-mplstp-config;
                    uses vpws-pseudowire-service-tpid-config;
                    uses vpws-pseudowire-static-config;
                    uses vpws-pseudowire-vccv-config;
                } // END of state-container definition.
            } // END of default-tagged-container definition.
            container tagged {
                when " not(/ipi-network-instance:network-instances/ipi-network-instance:network-instance/ipi-l2vpn-vpws:vpws-instance/ipi-l2vpn-vpws:pseudowire/ipi-l2vpn-vpws:default-tagged/ipi-l2vpn-vpws:config/ipi-l2vpn-vpws:enable-default-tagged-mode) + not(/ipi-network-instance:network-instances/ipi-network-instance:network-instance/ipi-l2vpn-vpws:vpws-instance/ipi-l2vpn-vpws:pseudowire/ipi-l2vpn-vpws:raw/ipi-l2vpn-vpws:config/ipi-l2vpn-vpws:enable-raw-mode) ";
                description
                    "Container for Tagged Fec128 pseudowire";
                container config {
                    presence "Create Tagged VPWS Fec-128 Instance";
                    description
                        "Configuration data for Tagged Fec128 pseudowire";
                    uses vpws-pseudowire-common-config;
                    uses vpws-pseudowire-mplstp-config;
                    uses vpws-pseudowire-static-config;
                    uses vpws-pseudowire-tagged-config;
                    uses vpws-pseudowire-vccv-config;
                } // END of config-container definition.
                container state {
                    config false;
                    description
                        "Container for Operational attributes for pseudowire";
                    uses vpws-pseudowire-common-config;
                    uses vpws-pseudowire-mplstp-config;
                    uses vpws-pseudowire-static-config;
                    uses vpws-pseudowire-tagged-config;
                    uses vpws-pseudowire-vccv-config;
                } // END of state-container definition.
            } // END of tagged-container definition.
            container raw {
                when " not(/ipi-network-instance:network-instances/ipi-network-instance:network-instance/ipi-l2vpn-vpws:vpws-instance/ipi-l2vpn-vpws:pseudowire/ipi-l2vpn-vpws:default-tagged/ipi-l2vpn-vpws:config/ipi-l2vpn-vpws:enable-default-tagged-mode) + not(/ipi-network-instance:network-instances/ipi-network-instance:network-instance/ipi-l2vpn-vpws:vpws-instance/ipi-l2vpn-vpws:pseudowire/ipi-l2vpn-vpws:tagged/ipi-l2vpn-vpws:config/ipi-l2vpn-vpws:enable-tagged-mode) ";
                description
                    "Container for Raw Fec128 pseudowire";
                container config {
                    presence "Create Raw VPWS Fec-128 Instance";
                    description
                        "Configuration data for Raw Fec128 pseudowire";
                    uses vpws-pseudowire-common-config;
                    uses vpws-pseudowire-mplstp-config;
                    uses vpws-pseudowire-raw-config;
                    uses vpws-pseudowire-static-config;
                    uses vpws-pseudowire-vccv-config;
                } // END of config-container definition.
                container state {
                    config false;
                    description
                        "Container for Operational attributes for pseudowire";
                    uses vpws-pseudowire-common-config;
                    uses vpws-pseudowire-mplstp-config;
                    uses vpws-pseudowire-raw-config;
                    uses vpws-pseudowire-static-config;
                    uses vpws-pseudowire-vccv-config;
                } // END of state-container definition.
            } // END of raw-container definition.
        } // End of pseudowire-list
    } // END of vpws-instance-container definition.
    } // END of vpws-instance-grouping definition.

    grouping  vpws-grouping {
    description
        "Top level container for vpws related configurations";
    container vpws {
        description
            "Top level container for vpws related configurations";
        uses vpws-interface-top;
        uses vpws-static-forwarding-top;
        uses vpws-global-state-top;
    } // END of vpws-container definition.
    } // END of vpws-grouping definition.

    augment /ipi-network-instance:network-instances/ipi-network-instance:network-instance {
    when " /ipi-network-instance:network-instances/ipi-network-instance:network-instance/ipi-network-instance:instance-type = 'vpws' ";
        description
            "Top level container for vpws instance";
        uses vpws-instance-grouping;
    }

    uses vpws-grouping;

    rpc pseudowire-trap-configuration {
        description "";
        input  {
            leaf status-notification  {
                type boolean;
                mandatory true;
                description "";
            }
            leaf delete-notification  {
                type boolean;
                mandatory true;
                description "";
            }
            leaf configure-notification  {
                type cml-data-types:cml_enable_disable_t;
                mandatory true;
                description "";
            }
        }
    }

    rpc clear-mpls-l2-circuit-statistics {
        description "";
        input  {
            leaf pseudowire-name  {
                type string;
                mandatory true;
                description "";
            }
        }
    }

    rpc clear-mpls-l2-circuit-port-statistics {
        description "";
        input  {
            leaf port-type  {
                type ipi-vpws-types:vpws_mpls_port_type_t;
                mandatory true;
                description "";
            }
            leaf port-pseudowire-name  {
                type string;
                mandatory true;
                description "";
            }
        }
    }

    rpc pseudowire-manual-switchover {
        description "";
        input  {
            leaf primary-pseudowire  {
                type string;
                mandatory true;
                description "";
            }
            leaf secondary-pseudowire  {
                type string;
                mandatory true;
                description "";
            }
        }
    }

    notification mpls-pseudowire-up {

        description "This notification is sent when pseusowire-state enters the up(4) state.";

        // severity "MINOR";
        // eventClass "STATE";
        leaf pseudowire-identifier {
            type  uint32;
        description
            "Use this attribute to assign pseudowire identifier to create an
                    instance of an MPLS layer 2 virtual circuit. A Layer-2 MPLS Virtual
                    Circuit instance may be bound to any interface on the router; however,
                    only one interface may be bound to a Layer-2 circuit at a time.";
        }

        leaf peer-address {
            type ipi-vpws-types:vpws_ip_addr_t;
        description
            "Use this attribute to specify pseudowire end peer IP address to create
                    an instance of an MPLS layer 2 virtual circuit";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.";
        }

        leaf pseudowire-state {
            type ipi-vpws-types:vpws_mpls_pw_state_t;
        description
            "This attribute provides local pseudowire state";
        }
    }

    notification mpls-pseudowire-down {

        description "This notification is sent when pseusowire-state enters the down(1) state.";

        // severity "CRITICAL";
        // eventClass "STATE";
        leaf pseudowire-identifier {
            type  uint32;
        description
            "Use this attribute to assign pseudowire identifier to create an
                    instance of an MPLS layer 2 virtual circuit. A Layer-2 MPLS Virtual
                    Circuit instance may be bound to any interface on the router; however,
                    only one interface may be bound to a Layer-2 circuit at a time.";
        }

        leaf peer-address {
            type ipi-vpws-types:vpws_ip_addr_t;
        description
            "Use this attribute to specify pseudowire end peer IP address to create
                    an instance of an MPLS layer 2 virtual circuit";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.";
        }

        leaf pseudowire-state {
            type ipi-vpws-types:vpws_mpls_pw_state_t;
        description
            "This attribute provides local pseudowire state";
        }
    }

    notification mpls-pseudowire-deleted {

        description "This notification is sent when pseusowire is deleted.";

        // severity "MINOR";
        // eventClass "STATE";
        leaf pseudowire-identifier {
            type  uint32;
        description
            "Use this attribute to assign pseudowire identifier to create an
                    instance of an MPLS layer 2 virtual circuit. A Layer-2 MPLS Virtual
                    Circuit instance may be bound to any interface on the router; however,
                    only one interface may be bound to a Layer-2 circuit at a time.";
        }

        leaf peer-address {
            type ipi-vpws-types:vpws_ip_addr_t;
        description
            "Use this attribute to specify pseudowire end peer IP address to create
                    an instance of an MPLS layer 2 virtual circuit";
        }

        leaf instance-type {
            type ipi-network-instance-types:net_inst_type_t;
        description
            "Network Instance Type";
        }

        leaf instance-name {
            type  string;
        description
            "Network Instance Name.
                    For VRF and MAC VRF, instance name can be up to 32 chars long.
                    For VPWS and VPLS instances, instance name can be up to 128 chars
                    long.
                    For L2NI (bridge) instance, instance name has to be a number between
                    (1-32).
                    For Cross-Connect, instance name can be up to 30 chars long.";
        }

        leaf pseudowire-state {
            type ipi-vpws-types:vpws_mpls_pw_state_t;
        description
            "This attribute provides local pseudowire state";
        }
    }

}

/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-acl.yang
*
*/

module ipi-acl {

    yang-version 1.1;

    namespace   "http://www.ipinfusion.com/yang/ocnos/ipi-acl";

    prefix "ipi-acl";

    import ipi-acl-types {
        prefix ipi-acl-types;
        revision-date 2022-01-20;
    }

    import cml-data-types {
        prefix cml-data-types;
        revision-date 2022-04-04;
    }

    import ipi-acl-common {
        prefix ipi-acl-common;
        revision-date 2021-09-17;
    }

    import ietf-yang-types {
        prefix yang;
        revision-date 2013-07-15;
    }

    import feature-list {
        prefix feature-list;
        revision-date 2022-07-13;
    }

    include ipi-acl-arp { revision-date 2021-09-17;}
    include ipi-acl-mac { revision-date 2021-09-17;}
    include ipi-acl-ports { revision-date 2021-11-16;}
    include ipi-acl-ipv6 { revision-date 2022-01-20;}
    organization
        "IP Infusion Inc.";

    contact
        "Address: 3965 Freedom Circle, Suite 200, Santa Clara, CA 95054
         Phone: +1 408-400-1900
         E-mail: support@ipinfusion.com
         Web: http://www.ipinfusion.com/";

    description
        "Datamodel for Access Control List (ACL) object";


    revision "2022-01-20" {
        description "Merged protocol-name and protocol-value into single attribute protocol-name";
        reference " 0.9.1.";
    }

    revision "2022-01-17" {
        description "Modified sub module";
        reference " 0.9.0.";
    }

    revision "2021-11-16" {
        description "Added some if-feature to fix customer SKU compilation";
        reference " 0.8.1.";
    }

    revision "2021-10-29" {
        description "Remove RDN from forwarding-action for IPv4 Standard ACLs";
        reference " 0.8.0.";
    }

    revision "2021-09-17" {
        description "Moved 'destination-mac-options' from ipi-acl-common module to ipi-acl-mac and ipi-acl-arp modules";
        reference " 0.7.0.";
    }

    revision "2021-09-03" {
        description "Update descriptions of attribute";
        reference " 0.6.0.";
    }

    revision "2021-08-18" {
        description "Updated sequence-id range to include the sequence-id of default icmpv6 entry, changed acl-entry to CONFIG_RUNTIME";
        reference " 0.5.0.";
    }

    revision "2021-08-16" {
        description "Added dependencies in acl-ports datamodel for correcting the order of API execution";
        reference " 0.4.0.";
    }

    revision "2021-08-02" {
        description "Changed acl-name as RDN in acl-ports datamodel";
        reference " 0.3.0.";
    }

    revision "2021-07-14" {
        description "Restructured module as per OpenConfig style";
        reference " 0.2.0.";
    }

    revision "2017-05-23" {
        description "Initial Version";
        reference " 0.1.0.";
    }

    grouping acl-set-config {
        description
            "Configuration data for ACL set";
        leaf name  {
            type  string {
                length "1..64";
                pattern "[a-zA-Z0-9][^?' =,>|]*";
            }
            description "The name of the access-list set";
        } // END of name definition.

        leaf type  {
            type  ipi-acl-types:acl_types_t;
            description "Type indicates the fields allowed in the ACL entries belonging to the
                        ACL set (e.g., ip, ipv6, etc.)";
        } // END of type definition.

        leaf description  {
            type  cml-data-types:cml_line_t {
                length "1..100";
            }
            description "Description, or comment, for the ACL set";
        } // END of description definition.

    } // END of acl-set-config definition.
    grouping acl-resequence-config {
        description
            "Configuration data for ACL resequencing";
        leaf starting-sequence-number  {
            type  uint32 {
                 range "1..268435453"  {
                    description "1..268435453:Starting sequence Number";
                 }
            }
            mandatory true;
            description "Use this attribute to set starting sequence number for resequencing";
        } // END of starting-sequence-number definition.

        leaf increment-steps  {
            type  uint32 {
                 range "1..268435453"  {
                    description "1..268435453:Sequence number increment steps";
                 }
            }
            mandatory true;
            description "Use this attribute to set increment steps for resequencing";
        } // END of increment-steps definition.

    } // END of acl-resequence-config definition.
    grouping acl-default-action-config {
        description
            "Configuration data for ACL default actions";
        leaf forwarding-action-default  {
            type  ipi-acl-types:acl_default_forwarding_action_t;
            mandatory true;
            description "Use this attribute to set default forwarding action";
        } // END of forwarding-action-default definition.

        leaf monitor-action-default  {
            if-feature feature-list:HAVE_SFLOW;
            if-feature feature-list:HAVE_CUSTOM1_ACL;
            type  ipi-acl-types:acl_monitor_action_t;
            description "Use this attribute to set default logging or sampling action";
        } // END of monitor-action-default definition.

    } // END of acl-default-action-config definition.
    grouping acl-default-counters {
        description
            "Default ACL entry counters";
        leaf matched-packets  {
            type  yang:counter64;
            config false;
            description "The number of packets that matched the default rule on the attached
                        interface.";
        } // END of matched-packets definition.

    } // END of acl-default-counters definition.
    grouping acl-sequence-id-config {
        description
            "sequence-id configuration for ACL entry";
        leaf sequence-id  {
            type  uint32 {
                 range "1..268435453"  {
                    description "1..268435453:ACL Sequence Number";
                 }
            }
            description "The sequence id determines the order in which ACL entries are applied.
                        The sequence id must be unique for each entry in an ACL set.";
        } // END of sequence-id definition.

    } // END of acl-sequence-id-config definition.
    grouping acl-ipv4-tcp-config {
        description
            "Configuration data specific for IPV4 TCP ACL entry";
        leaf tcp-flags  {
            type  ipi-acl-types:acl_tcp_flags_t;
            description "List of TCP flags to match";
        } // END of tcp-flags definition.

    } // END of acl-ipv4-tcp-config definition.
    grouping acl-ipv4-icmp-config {
        description
            "Configuration data specific for IPV4 ICMP ACL entry";
        leaf protocol-icmp  {
            type  empty;
            mandatory true;
            description "Use this attribute to indicates that protocol carried in the IP packet
                        is icmp.";
        } // END of protocol-icmp definition.

        leaf icmp-message  {
            if-feature feature-list:HAVE_CUSTOM1_ACL;
            type  ipi-acl-types:acl_icmp_options_t;
            description "Use this attribute to set ICMP message type";
        } // END of icmp-message definition.

        leaf icmp-type  {
            if-feature feature-list:HAVE_CUSTOM1_ACL;
            type  uint8 {
                 range "0..255"  {
                    description "0..255:icmp-type";
                 }
            }
            description "Use this attribute to set ICMP type";
        } // END of icmp-type definition.

        leaf icmp-code  {
            if-feature feature-list:HAVE_CUSTOM1_ACL;
            type  uint8 {
                 range "0..255"  {
                    description "0..255:icmp-code";
                 }
            }
            description "Use this attribute to set ICMP sub-type";
        } // END of icmp-code definition.

    } // END of acl-ipv4-icmp-config definition.
    grouping acl-ipv4-config {
        description
            "Configuration data for IPV4 ACL entry";
        leaf source-address  {
            type  ipi-acl-types:acl_any_ipv4_src_addr_t;
            mandatory true;
            description "Source IPv4 address prefix.";
        } // END of source-address definition.

        leaf destination-address  {
            type  ipi-acl-types:acl_any_ipv4_dest_addr_t;
            mandatory true;
            description "Destination IPv4 address prefix.";
        } // END of destination-address definition.

        leaf dscp  {
            type  ipi-acl-types:acl_dscp_t;
            description "Use this attribute to set the value of Differentiated Services Code
                        Point.";
        } // END of dscp definition.

        leaf precedence  {
            type  ipi-acl-types:acl_precedence_t;
            description "Use this attribute to set the precedence value";
        } // END of precedence definition.

        leaf inner-vlan-id  {
            type  uint16 {
                 range "1..4094"  {
                    description "1..4094:vlan  <1-4094>";
                 }
            }
            description "Use this attribute to set the inner-vlan-id";
        } // END of inner-vlan-id definition.

        choice protocol {
            description
                "Protocol Types";
            case tcp {

                description
                    "Transmission Control Protocol";

                uses ipi-acl-common:acl-tcp-config;
                uses acl-ipv4-tcp-config;
            }
            case udp {

                description
                    "User Datagram Protocol";

                uses ipi-acl-common:acl-udp-config;
            }
            case icmp {

                description
                    "Internet Control Message Protocol";

                uses acl-ipv4-icmp-config;
            }
            case other-protocols {

                description
                    "Other protocols";

                leaf protocol-name  {
                    type  ipi-acl-types:acl_ip_protocols_t;
                    mandatory true;
                    description "Use this attribute to set the protocol carried in the IP packet,
                                expressed by its name.";
                } // END of protocol-name definition.

            }
        } // END of protocol-choice definition.
    } // END of acl-ipv4-config definition.
    grouping acl-standard-config {
        description
            "Configuration data for Standard ACL set";
        leaf name  {
            type  string {
                length "1..64";
                pattern "[a-zA-Z0-9][^?' =,>|]*";
            }
            description "The name of the access-list set";
        } // END of name definition.

        leaf type  {
            type  ipi-acl-types:acl_standard_types_t;
            description "Type indicates the fields allowed in the ACL entries belonging to the
                        ACL set (ip, ipv6)";
        } // END of type definition.

    } // END of acl-standard-config definition.
    grouping acl-standard-ipv4-config {
        description
            "Configuration data for Standard IPV4 ACL set";
        leaf source-address  {
            type  ipi-acl-types:acl_any_ipv4_src_addr_t;
            description "Source IPv4 address prefix.";
        } // END of source-address definition.

        leaf forwarding-action  {
            type  ipi-acl-types:acl_forwarding_action_t;
            mandatory true;
            description "Specifies the forwarding action. One forwarding action must be
                        specified for each ACL entry.";
        } // END of forwarding-action definition.

    } // END of acl-standard-ipv4-config definition.
    grouping acl-entries-top {
        description
            "Top level grouping for ACL entries";
        container acl-entries {
            description
                "Container for ACL entries";

            list acl-entry {
                key "sequence-id";
                description
                    "List of ACL entries comprising an ACL set";
                leaf sequence-id  {
                    type  leafref {
                        path  "../config/sequence-id";
                    }
                    description "The sequence id determines the order in which ACL entries are applied.
                                The sequence id must be unique for each entry in an ACL set.";
                } // END of sequence-id definition.

                container config {
                    // when " ipi-acl:acl/acl-sets/acl-set/acl-entries/acl-entry/ipv4/config || ipi-acl-ipv6:ipv6/config || ipi-acl-mac:mac/config || ipi-acl-arp:arp/config ";
                    description
                        "ACL sequence-id configuration";
                    uses acl-sequence-id-config;
                } // END of config-container definition.
                container state {
                    config false;
                    description
                        "ACL sequence-id configuration";
                    uses acl-sequence-id-config;
                } // END of state-container definition.
                container ipv4 {
                    description
                        "IPV4 ACL set configuration attributes";
                    container config {
                        description
                            "ACL global configuration attributes";
                        uses ipi-acl-common:acl-common-config;
                        uses acl-ipv4-config;
                        uses ipi-acl-common:acl-ip-config;
                    } // END of config-container definition.
                    container state {
                        config false;
                        description
                            "Global Operational data for ACL";
                        container counters {
                            config false;
                            description
                                "Counter data for ACL entries";
                            uses ipi-acl-common:acl-counters;
                        } // END of counters-container definition.
                        uses ipi-acl-common:acl-common-config;
                        uses acl-ipv4-config;
                        uses ipi-acl-common:acl-ip-config;
                    } // END of state-container definition.
                    container fragment-actions {
                        if-feature feature-list:HAVE_CUSTOM1_ACL;
                        description
                            "Container for fragmented packet actions";
                        container config {
                            description
                                "Fragments action configuration attributes";
                            uses ipi-acl-common:acl-fragments-config;
                        } // END of config-container definition.
                        container state {
                            config false;
                            description
                                "Fragments action state information";
                            uses ipi-acl-common:acl-fragments-config;
                        } // END of state-container definition.
                    } // END of fragment-actions-container definition.
                } // END of ipv4-container definition.
                uses ipv6-grouping;
                uses arp-grouping;
                uses mac-grouping;
            } // End of acl-entry-list
        } // END of acl-entries-container definition.
    } // END of acl-entries-top definition.
    grouping acl-sets-top {
        description
            "Access list entries variables top level container";
        container acl-sets {
            description
                "Access list entries variables enclosing container";

            list acl-set {
                key "name type";
                description
                    "List of ACL sets, each comprising of a list of ACL entries";
                leaf name  {
                    type  leafref {
                        path  "../config/name";
                    }
                    description "The name of the access-list set";
                } // END of name definition.

                leaf type  {
                    type  leafref {
                        path  "../config/type";
                    }
                    description "Type indicates the fields allowed in the ACL entries belonging to the
                                ACL set (e.g., ip, ipv6, etc.)";
                } // END of type definition.

                container config {
                    description
                        "ACL set configuration attributes";
                    uses acl-set-config;
                } // END of config-container definition.
                container state {
                    config false;
                    description
                        "ACL set state information";
                    uses acl-set-config;
                } // END of state-container definition.
                container default-actions {
                    description
                        "Container for ACL default action related attributes";
                    container config {
                        description
                            "ACL default action related configuration attributes";
                        uses acl-default-action-config;
                    } // END of config-container definition.
                    container state {
                        config false;
                        description
                            "ACL default action related state information";
                        container counters {
                            config false;
                            description
                                "Counter data for Default ACL entry";
                            uses acl-default-counters;
                        } // END of counters-container definition.
                        uses acl-default-action-config;
                    } // END of state-container definition.
                } // END of default-actions-container definition.
                uses acl-entries-top;
                uses summary-info-grouping;
            } // End of acl-set-list
        } // END of acl-sets-container definition.
    } // END of acl-sets-top definition.
    grouping standard-acl-sets-top {
        description
            "Standard Access list entries variables top level container";
        container standard-acl-sets {
            description
                "Standard Access list entries variables enclosing container";

            list standard-acl-set {
                key "name type";
                description
                    "List of ACL sets, each comprising of a list of ACL entries";
                leaf name  {
                    type  leafref {
                        path  "../config/name";
                    }
                    description "The name of the access-list set";
                } // END of name definition.

                leaf type  {
                    type  leafref {
                        path  "../config/type";
                    }
                    description "Type indicates the fields allowed in the ACL entries belonging to the
                                standard ACL set (ip, ipv6)";
                } // END of type definition.

                container config {
                    description
                        "Standard ACL set configuration attributes";
                    uses acl-standard-config;
                } // END of config-container definition.
                container state {
                    config false;
                    description
                        "Standard ACL set state information";
                    uses acl-standard-config;
                } // END of state-container definition.
                container ipv4-acl-entries {
                    description
                        "Container for IPV4 Standard ACL entries";

                    list ipv4-acl-entry {
                        key "source-address";
                        description
                            "List of IPV4 ACL entries comprising an ACL set";
                        leaf source-address  {
                            type  leafref {
                                path  "../config/source-address";
                            }
                            description "Source IPv4 address prefix.";
                        } // END of source-address definition.

                        container config {
                            description
                                "Standard ACL set configuration attributes";
                            uses acl-standard-ipv4-config;
                        } // END of config-container definition.
                        container state {
                            config false;
                            description
                                "Standard ACL set state information";
                            uses acl-standard-ipv4-config;
                        } // END of state-container definition.
                    } // End of ipv4-acl-entry-list
                } // END of ipv4-acl-entries-container definition.
                uses ipv6-acl-entries-grouping;
            } // End of standard-acl-set-list
        } // END of standard-acl-sets-container definition.
    } // END of standard-acl-sets-top definition.

    grouping  acl-grouping {
    description
        "Top level container for ACL config and operational state data";
    container acl {
        description
            "Top level container for ACL config and operational state data";
        uses acl-sets-top;
        uses standard-acl-sets-top;
        uses interfaces-grouping;
        uses vty-line-grouping;
    } // END of acl-container definition.
    } // END of acl-grouping definition.

    uses acl-grouping;

    rpc clear-access-list-counters-all {
        description "Use this RPC to clear all access-list counters";
    }

    rpc clear-access-list-counters {
        description "Use this RPC to clear any specific ip access-list counter";
        input  {
            leaf name  {
                type string;
                mandatory true;
                description "The name of the access-list set";
            }
        }
    }

    rpc clear-ip-access-list-counters-all {
        description "Use this RPC to clear all ip access-list counters";
    }

    rpc clear-ip-access-list-counters {
        description "Use this RPC to clear any specific ip access-list counter";
        input  {
            leaf name  {
                type string;
                mandatory true;
                description "The name of the access-list set";
            }
        }
    }

    rpc clear-ipv6-access-list-counters-all {
        if-feature feature-list:HAVE_IPV6;
        description "Use this RPC to clear all ipv6 access-list counters";
    }

    rpc clear-ipv6-access-list-counters {
        if-feature feature-list:HAVE_IPV6;
        description "Use this RPC to clear any specific ipv6 access-list counter";
        input  {
            leaf name  {
                type string;
                mandatory true;
                description "The name of the access-list set";
            }
        }
    }

    rpc clear-mac-access-list-counters-all {
        description "Use this RPC to clear all mac access-list counters";
    }

    rpc clear-mac-access-list-counters {
        description "Use this RPC to clear any specific mac access-list counter";
        input  {
            leaf name  {
                type string;
                mandatory true;
                description "The name of the access-list set";
            }
        }
    }

    rpc clear-arp-access-list-counters-all {
        description "Use this RPC to clear all arp access-list counters";
    }

    rpc clear-arp-access-list-counters {
        description "Use this RPC to clear any specific arp access-list counter";
        input  {
            leaf name  {
                type string;
                mandatory true;
                description "The name of the access-list set";
            }
        }
    }

}

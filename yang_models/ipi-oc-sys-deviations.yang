module ipi-oc-sys-deviations {
  namespace   "http://www.ipinfusion.com/yang/ocnos/ipi-oc-sys-deviations";
  prefix "ipi-oc-sys-deviations";

  import openconfig-system { prefix oc-sys; }

  revision "2022-01-19" {
    description "Added new deviations for not supported trees";
  }

  revision "2021-05-04" {
    description "Date/time notation is wrong for OpenConfig,
                 see https://github.com/openconfig/public/issues/166";
  }

  revision "2020-11-24";

  deviation /oc-sys:system/oc-sys:logging/oc-sys:console {
    deviate not-supported;
  }

  deviation /oc-sys:system/oc-sys:logging/oc-sys:remote-servers/oc-sys:remote-server/oc-sys:selectors/oc-sys:selector {
    deviate add {
      max-elements 1;
    }
  }

  augment /oc-sys:system/oc-sys:logging/oc-sys:remote-servers {
    container config {
      leaf vrf {
        type string;
      }
    }
    container state {
      config false;
      leaf vrf {
        type string;
      }
    }
  }

  deviation /oc-sys:system/oc-sys:state/oc-sys:current-datetime {
    deviate replace {
      type string;
    }
  }

  augment /oc-sys:system/oc-sys:alarms/oc-sys:alarm/oc-sys:state {
    leaf alarm-reported-timestamp {
      type string;
    }
  }

  deviation /oc-sys:system/oc-sys:config/oc-sys:login-banner {
    deviate not-supported;
  }

  deviation /oc-sys:system/oc-sys:state/oc-sys:login-banner {
    deviate not-supported;
  }

  deviation /oc-sys:system/oc-sys:config/oc-sys:motd-banner {
    deviate not-supported;
  }

  deviation /oc-sys:system/oc-sys:state/oc-sys:motd-banner {
    deviate not-supported;
  }

  deviation /oc-sys:system/oc-sys:state/oc-sys:boot-time {
    deviate not-supported;
  }

  deviation /oc-sys:system/oc-sys:aaa {
    deviate not-supported;
  }

  deviation /oc-sys:system/oc-sys:dns {
    deviate not-supported;
  }

  deviation /oc-sys:system/oc-sys:ntp {
    deviate not-supported;
  }

  deviation /oc-sys:system/oc-sys:ssh-server {
    deviate not-supported;
  }

  deviation /oc-sys:system/oc-sys:telnet-server {
    deviate not-supported;
  }

  deviation /oc-sys:system/oc-sys:memory {
    deviate not-supported;
  }

  deviation /oc-sys:system/oc-sys:cpus {
    deviate not-supported;
  }

  deviation /oc-sys:system/oc-sys:processes {
    deviate not-supported;
  }

  deviation /oc-sys:system/oc-sys:messages {
    deviate not-supported;
  }

  deviation /oc-sys:system/oc-sys:license {
    deviate not-supported;
  }
}

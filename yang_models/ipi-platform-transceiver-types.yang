/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform-transceiver-types.yang
*
*/

module ipi-platform-transceiver-types {

    yang-version 1.1;

    namespace   "http://www.ipinfusion.com/yang/ocnos/ipi-platform-transceiver-types";

    prefix "ipi-platform-transceiver-types";

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-platform-transceiver-types";


    revision "2021-09-03" {
        description "Update descriptions of attribute";
        reference "Initial Version";
    }

    revision "2021-06-01" {
        description "New Types added";
        reference " 0.3.0.";
    }

    revision "2020-12-15" {
        description "Change to have data-types in lower case instead of camel case";
        reference " 0.2.0.";
    }

    revision "2018-06-21" {
        description "Initial Version";
        reference " 0.1.0.";
    }



    typedef  ddm_transceiver_t {
        type enumeration {
            enum 1000base-sx {
                value 1;
                description "sfp 1000base-sx";
            }
            enum 1000base-lx {
                value 2;
                description "sfp 1000base-lx";
            }
            enum 1000base-ex {
                value 3;
                description "sfp 1000base-ex";
            }
            enum 1000base-cx {
                value 4;
                description "sfp 1000base-cx";
            }
            enum 10gbase-sr {
                value 5;
                description "sfp+ 10gbase-sr";
            }
            enum 10gbase-lr {
                value 6;
                description "sfp+ 10gbase-lr";
            }
            enum 10gbase-er {
                value 7;
                description "sfp+ 10gbase-er";
            }
            enum 10gbase-cr {
                value 8;
                description "sfp+ 10gbase-cr";
            }
            enum 25gbase-sr {
                value 9;
                description "sfp+ 25gbase-sr";
            }
            enum 25gbase-lr {
                value 10;
                description "sfp+ 25gbase-lr";
            }
            enum 25gbase-er {
                value 11;
                description "sfp+ 25gbase-er";
            }
            enum 25gbase-cr {
                value 12;
                description "sfp+ 25gbase-cr";
            }
            enum 40gbase-sr4 {
                value 13;
                description "qsfp 40gbase-sr4";
            }
            enum 40gbase-lr4 {
                value 14;
                description "qsfp 40gbase-lr4";
            }
            enum 40gbase-er4 {
                value 15;
                description "qsfp 40gbase-er4";
            }
            enum 40gbase-cr4 {
                value 16;
                description "qsfp 40gbase-cr4";
            }
            enum 100gbase-sr4 {
                value 17;
                description "qsfp28 100gbase-sr4";
            }
            enum 100gbase-lr4 {
                value 18;
                description "qsfp28 100gbase-lr4";
            }
            enum 100gbase-er4 {
                value 19;
                description "qsfp28 100gbase-er4";
            }
            enum 100gbase-cr4 {
                value 20;
                description "qsfp28 100gbase-cr4";
            }
        }
        description "type definition for DDM_TRANSCEIVER_T";
    }

    typedef  ddm_cmm_trans_type_t {
        type enumeration {
            enum sfp {
                value 1;
                description "trans type sfp";
            }
            enum qsfp {
                value 2;
                description "trans type qsfp";
            }
            enum xfp {
                value 3;
                description "trans type xfp";
            }
            enum pon-xfp {
                value 4;
                description "trans type pon xfp";
            }
            enum unknown {
                value 5;
                description "trans type unknown";
            }
        }
        description "type definition for DDM_CMM_TRANS_TYPE_T";
    }

    typedef  ddm_cmm_trans_presence_t {
        type enumeration {
            enum Not-Present {
                value 0;
                description "Transceiver Not present";
            }
            enum Present {
                value 1;
                description "Transceiver Present";
            }
        }
        description "type definition for DDM_CMM_TRANS_PRESENCE_T";
    }

    typedef  ddm_cmm_trans_reset_t {
        type enumeration {
            enum NA {
                value 0;
                description "Not Applicable";
            }
            enum Reset {
                value 1;
                description "In Reset";
            }
            enum Normal {
                value 2;
                description "Out of Reset";
            }
        }
        description "type definition for DDM_CMM_TRANS_RESET_T";
    }

    typedef  ddm_tx_rx_state_t {
        type enumeration {
            enum NA {
                value 0;
                description "Not Applicable";
            }
            enum off {
                value 1;
                description "off";
            }
            enum on {
                value 2;
                description "on";
            }
        }
        description "type definition for DDM_TX_RX_STATE_T";
    }

    typedef  ddm_cmm_trans_power_t {
        type enumeration {
            enum NA {
                value 0;
                description "Not Applicable";
            }
            enum Low {
                value 1;
                description "Power low";
            }
            enum High {
                value 2;
                description "Power high";
            }
        }
        description "type definition for DDM_CMM_TRANS_POWER_T";
    }

    typedef  ddm_cmm_trans_identifier_t {
        type enumeration {
            enum unknown {
                value 1;
                description "trans identifier unknown";
            }
            enum gbic {
                value 2;
                description "trans identifier gbic";
            }
            enum soldered-to-motherboard {
                value 3;
                description "trans identifier soldered-to-motherboard";
            }
            enum sfp-or-sfpplus-or-sfp28 {
                value 4;
                description "trans identifier sfp-or-sfpplus-or-sfp28";
            }
            enum xbi-300pin {
                value 5;
                description "trans identifier xbi-300pin";
            }
            enum xenpak {
                value 6;
                description "trans identifier xenpak";
            }
            enum xfp {
                value 7;
                description "trans identifier xfp";
            }
            enum xff {
                value 8;
                description "trans identifier xff";
            }
            enum xfpe {
                value 9;
                description "trans identifier xfpe";
            }
            enum xpak {
                value 10;
                description "trans identifier xpak";
            }
            enum x2 {
                value 11;
                description "trans identifier x2";
            }
            enum dwdmsfp-or-dwdmsfpplus {
                value 12;
                description "trans identifier dwdmsfp-or-dwdmsfpplus";
            }
            enum qsfp {
                value 13;
                description "trans identifier qsfp";
            }
            enum qsfpplus-or-later {
                value 14;
                description "trans identifier qsfpplus-or-later";
            }
            enum cxp-or-later {
                value 15;
                description "trans identifier cxp-or-later";
            }
            enum shielded-mini-multilane-hd4x {
                value 16;
                description "trans identifier shielded-mini-multilane-hd4x";
            }
            enum shielded-mini-multilane-hd8x {
                value 17;
                description "trans identifier shielded-mini-multilane-hd8x";
            }
            enum qsfp28-or-later {
                value 18;
                description "trans identifier qsfp28-or-later";
            }
            enum cxp2-aka-cxp28-or-later {
                value 19;
                description "trans identifier cxp2-aka-cxp28-or-later";
            }
            enum cdfpstyle1-or-cdfpstyle2 {
                value 20;
                description "trans identifier cdfpstyle1-or-cdfpstyle2";
            }
            enum shielded-mini-multilane-hd4x-fanoutcable {
                value 21;
                description "trans identifier shielded-mini-multilane-hd4x-fanoutcable";
            }
            enum shielded-mini-multilane-hd8x-fanoutcable {
                value 22;
                description "trans identifier shielded-mini-multilane-hd8x-fanoutcable";
            }
            enum cdfpstyle3 {
                value 23;
                description "trans identifier cdfpstyle3";
            }
            enum microqsfp {
                value 24;
                description "trans identifier microqsfp";
            }
            enum qsfp-doubledensity-8x-pluggable-transceiver {
                value 25;
                description "trans identifier qsfp-doubledensity-8x-pluggable-transceiver";
            }
            enum reserved {
                value 26;
                description "trans identifier reserved";
            }
            enum vendor-specific {
                value 27;
                description "trans identifier vendor-specific";
            }
        }
        description "type definition for DDM_CMM_TRANS_IDENTIFIER_T";
    }

    typedef  ddm_cmm_trans_sfp_extended_identifier_t {
        type enumeration {
            enum gbic-notspecified-or-compliant-with-moddef {
                value 1;
                description "sfp ext-identifier gbic-notspecified-or-compliant-with-moddef ";
            }
            enum gbic-compliant-with-moddef1 {
                value 2;
                description "sfp ext-identifier gbic-compliant-with-moddef1";
            }
            enum gbic-compliant-with-moddef2 {
                value 3;
                description "sfp ext-identifier gbic-compliant-with-moddef2";
            }
            enum gbic-compliant-with-moddef3 {
                value 4;
                description "sfp ext-identifier gbic-compliant-with-moddef3";
            }
            enum gbic-or-sfp-definedby-twowire-interfaceid-only {
                value 5;
                description "sfp ext-identifier gbic-or-sfp-definedby-twowire-interfaceid-only";
            }
            enum gbic-compliant-with-moddef5 {
                value 6;
                description "sfp ext-identifier gbic-compliant-with-moddef5";
            }
            enum gbic-compliant-with-moddef6 {
                value 7;
                description "sfp ext-identifier gbic-compliant-with-moddef6";
            }
            enum gbic-compliant-with-moddef7 {
                value 8;
                description "sfp ext-identifier gbic-compliant-with-moddef7";
            }
            enum unallocated {
                value 9;
                description "sfp ext-identifier unallocated";
            }
            enum unknown {
                value 10;
                description "sfp ext-identifier unknown";
            }
        }
        description "type definition for DDM_CMM_TRANS_SFP_EXTENDED_IDENTIFIER_T";
    }

    typedef  ddm_cmm_qsfp_extended_identifier_t {
        type bits {
            bit powerclass1-1dot5wmax {
                position 0;
                description "qsfp ext-identifier powerclass1-1dot5wmax";
            }
            bit powerclass2-2wmax {
                position 1;
                description "qsfp ext-identifier powerclass2-2wmax";
            }
            bit powerclass3-2dot5wmax {
                position 2;
                description "qsfp ext-identifier powerclass3-2dot5wmax";
            }
            bit powerclass4-3dot5wmax {
                position 3;
                description "qsfp ext-identifier powerclass4-3dot5wmax";
            }
            bit cleicode-present {
                position 4;
                description "qsfp ext-identifier cleicode-present";
            }
            bit cdrpresent-in-tx {
                position 5;
                description "qsfp ext-identifier cdrpresent-in-tx";
            }
            bit cdrpresent-in-rx {
                position 6;
                description "qsfp ext-identifier cdrpresent-in-rx";
            }
            bit powerclass5-4wmax {
                position 7;
                description "qsfp ext-identifier powerclass5-4wmax";
            }
            bit powerclass6-4dot5wmax {
                position 8;
                description "qsfp ext-identifier powerclass6-4dot5wmax";
            }
            bit powerclass7-5wmax {
                position 9;
                description "qsfp ext-identifier powerclass7-5wmax";
            }
        }
        description "type definition for DDM_CMM_QSFP_EXTENDED_IDENTIFIER_T";
    }

    typedef  ddm_cmm_trans_xfp_extended_identifier_t {
        type bits {
            bit powerlevel1-1dot5wmax {
                position 0;
                description "XFP power level 1 with maximum 1.5w";
            }
            bit powerlevel2-2dot5wmax {
                position 1;
                description "XFP power level 2 with maximum 2.5w";
            }
            bit powerlevel3-3dot5wmax {
                position 2;
                description "XFP power level 3 with maximum 3.5w";
            }
            bit powerlevel4-over3dot5w {
                position 3;
                description "XFP power level 4 with over3.5w";
            }
            bit cdr-none {
                position 4;
                description "XFP CDR unsupported";
            }
            bit txrefclk-input-notrequired {
                position 5;
                description "XFP Tx RefClock input unrequired";
            }
            bit cleicode-present {
                position 6;
                description "XFP CLEI code present in table 2";
            }
        }
        description "type definition for DDM_CMM_TRANS_XFP_EXTENDED_IDENTIFIER_T";
    }

    typedef  ddm_cmm_trans_connector_type_t {
        type enumeration {
            enum unknown {
                value 1;
                description "trans connector unknown";
            }
            enum subscriber-connector {
                value 2;
                description "trans connector subscriber-connector";
            }
            enum fibrechannel-style1-copperconnector {
                value 3;
                description "trans connector fibrechannel-style1-copperconnector";
            }
            enum fibrechannel-style2-copperconnector {
                value 4;
                description "trans connector fibrechannel-style2-copperconnector";
            }
            enum bayonet-or-threaded-neill-concelman {
                value 5;
                description "trans connector bayonet-or-threaded-neill-concelman";
            }
            enum fibrechannel-coaxheaders {
                value 6;
                description "trans connector fibrechannel-coaxheaders";
            }
            enum fiber-jack {
                value 7;
                description "trans connector fiber-jack";
            }
            enum lucent-connector {
                value 8;
                description "trans connector lucent-connector";
            }
            enum mechanical-transfer-registeredjack {
                value 9;
                description "trans connector mechanical-transfer-registeredjack";
            }
            enum multiple-optical {
                value 10;
                description "trans connector multiple-optical";
            }
            enum sg {
                value 11;
                description "trans connector sg";
            }
            enum optical-pigtail {
                value 12;
                description "trans connector optical-pigtail";
            }
            enum multifiber-paralleloptic-1x12 {
                value 13;
                description "trans connector multifiber-paralleloptic-1x12";
            }
            enum multifiber-paralleloptic-1x16 {
                value 14;
                description "trans connector multifiber-paralleloptic-1x16";
            }
            enum hssdcii {
                value 15;
                description "trans connector hssdcii";
            }
            enum copper-pigtail {
                value 16;
                description "trans connector copper-pigtail";
            }
            enum rj45 {
                value 17;
                description "trans connector rj45";
            }
            enum no-separable-connector {
                value 18;
                description "trans connector no-separable-connector";
            }
            enum mxc2-x16 {
                value 19;
                description "trans connector mxc2-x16";
            }
            enum reserved {
                value 20;
                description "trans connector reserved";
            }
            enum vendor-specific {
                value 21;
                description "trans connector vendor-specific";
            }
        }
        description "type definition for DDM_CMM_TRANS_CONNECTOR_TYPE_T";
    }

    typedef  ddm_cmm_trans_eth_compliance_t {
        type enumeration {
            enum ec-unknown {
                value 1;
                description "trans compliance ec-unknown";
            }
            enum ec-10gbase-sr {
                value 2;
                description "trans compliance ec-10gbase-sr";
            }
            enum ec-10gbase-lr {
                value 3;
                description "trans compliance ec-10gbase-lr";
            }
            enum ec-10gbase-lrm {
                value 4;
                description "trans compliance ec-10gbase-lrm";
            }
            enum ec-10gbase-er {
                value 5;
                description "trans compliance ec-10gbase-er";
            }
            enum ec-1000base-sx {
                value 6;
                description "trans compliance ec-1000base-sx";
            }
            enum ec-1000base-lx {
                value 7;
                description "trans compliance ec-1000base-lx";
            }
            enum ec-1000base-cx {
                value 8;
                description "trans compliance ec-1000base-cx";
            }
            enum ec-1000base-t {
                value 9;
                description "trans compliance ec-1000base-t";
            }
            enum ec-100base-lx-or-lx10 {
                value 10;
                description "trans compliance ec-100base-lx-or-lx10";
            }
            enum ec-100base-fx {
                value 11;
                description "trans compliance ec-100base-fx";
            }
            enum ec-base-bx10 {
                value 12;
                description "trans compliance ec-base-bx10";
            }
            enum ec-base-px {
                value 13;
                description "trans compliance ec-base-px";
            }
            enum ec-40gbase-cr4 {
                value 14;
                description "trans compliance ec-40gbase-cr4";
            }
            enum ec-40gbase-sr4 {
                value 15;
                description "trans compliance ec-40gbase-sr4";
            }
            enum ec-40gbase-lr4 {
                value 16;
                description "trans compliance ec-40gbase-lr4";
            }
            enum ec-40g-activecable {
                value 17;
                description "trans compliance ec-40g-activecable";
            }
        }
        description "type definition for DDM_CMM_TRANS_ETH_COMPLIANCE_T";
    }

    typedef  ddm_cmm_trans_ext_eth_compliance_t {
        type bits {
            bit eec-unspecified {
                position 0;
                description "trans ext compliance eec-unspecified";
            }
            bit eec-100g-activeopticalcable-or-25g-auic2maoc {
                position 1;
                description "transext compliance eec-100g-activeopticalcable-or-25g-auic2maoc";
            }
            bit eec-100gbase-sr4-or-25gbase-sr {
                position 2;
                description "trans ext compliance eec-100gbase-sr4-or-25gbase-sr";
            }
            bit eec-100gbase-lr4-or-25gbase-lr {
                position 3;
                description "trans ext compliance eec-100gbase-lr4-or-25gbase-lr";
            }
            bit eec-100gbase-er4-or-25gbase-er {
                position 4;
                description "trans ext compliance eec-100gbase-er4-or-25gbase-er";
            }
            bit eec-100gbase-sr10 {
                position 5;
                description "trans ext compliance eec-100gbase-sr10";
            }
            bit eec-100g-cwdm4 {
                position 6;
                description "trans ext compliance eec-100g-cwdm4";
            }
            bit eec-100g-psm4-parallelsmf {
                position 7;
                description "trans ext compliance eec-100g-psm4-parallelsmf";
            }
            bit eec-100g-activecoppercable-or-25g-auic2macc {
                position 8;
                description "trans ext compliance eec-100g-activecoppercable-or-25g-auic2macc";
            }
            bit eec-obsolete {
                position 9;
                description "trans ext compliance eec-obsolete";
            }
            bit eec-reserved {
                position 10;
                description "trans ext compliance eec-reserved";
            }
            bit eec-100gbase-cr4-or-25gbase-crca-l {
                position 11;
                description "trans ext compliance eec-100gbase-cr4-or-25gbase-crca-l";
            }
            bit eec-25gbase-crca-s {
                position 12;
                description "trans ext compliance eec-25gbase-crca-s";
            }
            bit eec-25gbase-crca-n {
                position 13;
                description "trans ext compliance eec-25gbase-crca-n";
            }
            bit eec-40gbase-er4 {
                position 14;
                description "trans ext compliance eec-40gbase-er4";
            }
            bit eec-4x10gbase-sr {
                position 15;
                description "trans ext compliance eec-4x10gbase-sr";
            }
            bit eec-40g-psm4-parallelsmf {
                position 16;
                description "trans ext compliance eec-40g-psm4-parallelsmf";
            }
            bit eec-g959-dot1-profilep1-i1-2d1 {
                position 17;
                description "trans ext compliance eec-g959-dot1-profilep1-i1-2d1";
            }
            bit eec-g959-dot1-profilep1-s1-2d2 {
                position 18;
                description "trans ext compliance eec-g959-dot1-profilep1-s1-2d2";
            }
            bit eec-g959-dot1-profilep1-l1-2d2 {
                position 19;
                description "trans ext compliance eec-g959-dot1-profilep1-l1-2d2";
            }
            bit eec-100gbase-t-with-sfi-electricalinterface {
                position 20;
                description "trans ext compliance eec-100gbase-t-with-sfi-electricalinterface";
            }
            bit eec-100g-clr4 {
                position 21;
                description "trans ext compliance eec-100g-clr4";
            }
            bit eec-100g-aoc-or-25g-auic2maoc {
                position 22;
                description "trans ext compliance eec-100g-aoc-or-25g-auic2maoc";
            }
            bit eec-100g-acc-or-25g-auic2macc {
                position 23;
                description "trans ext compliance eec-100g-acc-or-25g-auic2macc";
            }
            bit eec-100ge-dwdm2 {
                position 24;
                description "trans ext compliance eec-100ge-dwdm2";
            }
            bit null {
                position 31;
                description "NULL";
            }
        }
        description "type definition for DDM_CMM_TRANS_EXT_ETH_COMPLIANCE_T";
    }

    typedef  ddm_cmm_trans_sonet_compliance_t {
        type bits {
            bit oc192-shortreach {
                position 0;
                description "oc192-shortreach";
            }
            bit sonet-reachspecifier-bit1 {
                position 1;
                description "sonet-reachspecifier-bit1";
            }
            bit sonet-reachspecifier-bit2 {
                position 2;
                description "sonet-reachspecifier-bit2";
            }
            bit oc48-longreach {
                position 3;
                description "oc48-longreach";
            }
            bit oc48-intermediatereach {
                position 4;
                description "oc48-intermediatereach";
            }
            bit oc48-shortreach {
                position 5;
                description "oc48-shortreach";
            }
            bit oc12-singlemode-longreach {
                position 6;
                description "oc12-singlemode-longreach";
            }
            bit oc12-singlemode-intermediatereach {
                position 7;
                description "oc12-singlemode-intermediatereach";
            }
            bit oc12-singlemode-shortreach {
                position 8;
                description "oc12-singlemode-shortreach";
            }
            bit oc3-singlemode-longreach {
                position 9;
                description "oc3-singlemode-longreach";
            }
            bit oc3-singlemode-intermediatereach {
                position 10;
                description "oc3-singlemode-intermediatereach";
            }
            bit oc3-singlemode-shortreach {
                position 11;
                description "oc3-singlemode-shortreach";
            }
            bit null {
                position 31;
                description "NULL";
            }
        }
        description "type definition for DDM_CMM_TRANS_SONET_COMPLIANCE_T";
    }

    typedef  ddm_cmm_trans_fiber_channel_linklen_t {
        type bits {
            bit short {
                position 0;
                description "short";
            }
            bit medium {
                position 1;
                description "medium";
            }
            bit intermediate {
                position 2;
                description "intermediate";
            }
            bit long {
                position 3;
                description "long";
            }
            bit verylong {
                position 4;
                description "very long";
            }
            bit null {
                position 31;
                description "NULL";
            }
        }
        description "type definition for DDM_CMM_TRANS_FIBER_CHANNEL_LINKLEN_T";
    }

    typedef  ddm_cmm_trans_fiber_channel_transmittech_t {
        type bits {
            bit shortwaveLaserLinearRx {
                position 0;
                description "shortwaveLaserLinearRx";
            }
            bit longwaveLaserLC {
                position 1;
                description "longwaveLaser LC";
            }
            bit electricalInter-Enclosure {
                position 2;
                description "electricalInter-Enclosure";
            }
            bit electricalIntra-Enclosure {
                position 3;
                description "electricalIntra-Enclosure";
            }
            bit shortwaveLaserWithOutOFC {
                position 4;
                description "shortwaveLaserWithOutOFC";
            }
            bit shortwaveLaserwithOFC {
                position 5;
                description "shortwaveLaserwithOFC";
            }
            bit longwaveLaserLL {
                position 6;
                description "longwaveLaser LL";
            }
            bit null {
                position 31;
                description "NULL";
            }
        }
        description "type definition for DDM_CMM_TRANS_FIBER_CHANNEL_TRANSMITTECH_T";
    }

    typedef  ddm_cmm_trans_fiber_channel_transmitmedia_t {
        type bits {
            bit twinaxial-pair {
                position 0;
                description "twinaxial-pair";
            }
            bit twisted-pair {
                position 1;
                description "twisted-pair";
            }
            bit miniature-coax {
                position 2;
                description "miniature-coax";
            }
            bit video-coax {
                position 3;
                description "video-coax";
            }
            bit multi-mode62dot5m {
                position 4;
                description "multi-mode62dot5m";
            }
            bit multi-mode50m {
                position 5;
                description "multi-mode50m";
            }
            bit multi-mode50um {
                position 6;
                description "multi-mode50um";
            }
            bit single-mode {
                position 7;
                description "single-mode";
            }
            bit null {
                position 31;
                description "NULL";
            }
        }
        description "type definition for DDM_CMM_TRANS_FIBER_CHANNEL_TRANSMITMEDIA_T";
    }

    typedef  ddm_cmm_trans_fiber_channel_speed_t {
        type bits {
            bit fcs-3200mbps {
                position 0;
                description "fcs-3200mbps";
            }
            bit fcs-1600mbps {
                position 1;
                description "fcs-1600mbps";
            }
            bit fcs-1200mbps {
                position 2;
                description "fcs-1200mbps";
            }
            bit fcs-800mbps {
                position 3;
                description "fcs-800mbps";
            }
            bit fcs-400mbps {
                position 4;
                description "fcs-400mbps";
            }
            bit fcs-200mbps {
                position 5;
                description "fcs-200mbps";
            }
            bit fcs-100mbps {
                position 6;
                description "fcs-100mbps";
            }
            bit null {
                position 31;
                description "NULL";
            }
        }
        description "type definition for DDM_CMM_TRANS_FIBER_CHANNEL_SPEED_T";
    }

    typedef  ddm_cmm_trans_sfp_infiniband_compliance_t {
        type enumeration {
            enum ibc-1xsx {
                value 1;
                description "ibc-1xsx";
            }
            enum ibc-1xlx {
                value 2;
                description "ibc-1xlx";
            }
            enum ibc-1xcopperactive {
                value 3;
                description "ibc-1xcopperactive";
            }
            enum ibc-1xcopperpassive {
                value 4;
                description "ibc-1xcopperpassive";
            }
            enum ibc-unknown {
                value 5;
                description "ibc-unknown";
            }
            enum ibc-notapplicable {
                value 6;
                description "ibc-notapplicable";
            }
        }
        description "type definition for DDM_CMM_TRANS_SFP_INFINIBAND_COMPLIANCE_T";
    }

    typedef  ddm_cmm_trans_sfp_escon_compliance_t {
        type enumeration {
            enum escon-mmf-1310nm-led {
                value 1;
                description "escon-mmf-1310nm-led";
            }
            enum escon-smf-1310nm-laser {
                value 2;
                description "escon-smf-1310nm-laser";
            }
            enum unknown {
                value 3;
                description "unknown";
            }
            enum notapplicable {
                value 4;
                description "notapplicable";
            }
        }
        description "type definition for DDM_CMM_TRANS_SFP_ESCON_COMPLIANCE_T";
    }

    typedef  ddm_cmm_trans_sfp_plus_cable_tech_t {
        type enumeration {
            enum active {
                value 1;
                description "active";
            }
            enum passive {
                value 2;
                description "passive";
            }
            enum unknown {
                value 3;
                description "unknown";
            }
            enum notapplicable {
                value 4;
                description "notapplicable";
            }
        }
        description "type definition for DDM_CMM_TRANS_SFP_PLUS_CABLE_TECH_T";
    }

    typedef  ddm_cmm_trans_xfp_10g_eth_compliance_t {
        type bits {
            bit xec-10gbase-sr {
                position 0;
                description "Transceiver ethernet compliance 10GBASE-SR";
            }
            bit xec-10gbase-lr {
                position 1;
                description "Transceiver ethernet compliance 10GBASE-LR";
            }
            bit xec-10gbase-er {
                position 2;
                description "Transceiver ethernet compliance 10GBASE-ER";
            }
            bit xec-10gbase-lrm {
                position 3;
                description "Transceiver ethernet compliance 10GBASE-LRM";
            }
            bit xec-10gbase-sw {
                position 4;
                description "Transceiver ethernet compliance 10GBASE-SW";
            }
            bit xec-10gbase-lw {
                position 5;
                description "Transceiver ethernet compliance 10GBASE-LW";
            }
            bit xec-10gbase-ew {
                position 6;
                description "Transceiver ethernet compliance 10GBASE-EW";
            }
        }
        description "type definition for DDM_CMM_TRANS_XFP_10G_ETH_COMPLIANCE_T";
    }

    typedef  ddm_cmm_trans_xfp_10g_fiber_chn_compliance_t {
        type bits {
            bit xfcc-1200-mx-sn-i {
                position 0;
                description "Transceiver fiber channel compliance 1200-MX-SN-I";
            }
            bit xfcc-1200-sm-ll-l {
                position 1;
                description "Transceiver fiber channel compliance 1200-SM-LL-L";
            }
            bit xfcc-exended-reach-1550nm {
                position 2;
                description "Transceiver fiber channel compliance Extended Reach 1550 nm";
            }
            bit xfcc-intermediate-reach-1300nm-fp {
                position 3;
                description "Transceiver fiber channel compliance Intermediate Reach 1300 nm FP";
            }
        }
        description "type definition for DDM_CMM_TRANS_XFP_10G_FIBER_CHN_COMPLIANCE_T";
    }

    typedef  ddm_cmm_trans_xfp_10g_copper_links_rsvd_t {
        type bits {
            bit xcl-rsvd {
                position 0;
                description "Transceiver 10G Copper links reserved";
            }
        }
        description "type definition for DDM_CMM_TRANS_XFP_10G_COPPER_LINKS_RSVD_T";
    }

    typedef  ddm_cmm_trans_xfp_lower_speed_links_t {
        type bits {
            bit xlsl-1000base-sx {
                position 0;
                description "Transceiver 1000BASE-SX/1xFC MMF";
            }
            bit xlsl-1000base-lx {
                position 1;
                description "Transceiver 1000BASE-LX/1xFC SMF";
            }
            bit xlsl-2xfc-mmf {
                position 2;
                description "Transceiver 2xFC MMF";
            }
            bit xlsl-2xfc-smf {
                position 3;
                description "Transceiver 2xFC SMF";
            }
            bit xlsl-oc48-sr {
                position 4;
                description "Transceiver OC 48-SR";
            }
            bit xlsl-oc48-ir {
                position 5;
                description "Transceiver OC 48-IR";
            }
            bit xlsl-oc48-lr {
                position 6;
                description "Transceiver OC 48-LR";
            }
        }
        description "type definition for DDM_CMM_TRANS_XFP_LOWER_SPEED_LINKS_T";
    }

    typedef  ddm_cmm_trans_xfp_sonet_interconnect_t {
        type bits {
            bit xsi-i-64-lr {
                position 0;
                description "SONET/SDH compliant code I-64.1r";
            }
            bit xsi-i-64-l {
                position 1;
                description "SONET/SDH compliant code I-64.1";
            }
            bit xsi-i-64-2r {
                position 2;
                description "SONET/SDH compliant code I-64.2r";
            }
            bit xsi-i-64-2 {
                position 3;
                description "SONET/SDH compliant code I-64.2";
            }
            bit xsi-i-64-3 {
                position 4;
                description "SONET/SDH compliant code I-64.3";
            }
            bit xsi-i-64-5 {
                position 5;
                description "SONET/SDH compliant code I-64.5";
            }
        }
        description "type definition for DDM_CMM_TRANS_XFP_SONET_INTERCONNECT_T";
    }

    typedef  ddm_cmm_trans_xfp_sonet_short_haul_t {
        type bits {
            bit xssh-s-64-l {
                position 0;
                description "SONET/SDH compliant code S-64.1r";
            }
            bit xssh-s-64-2a {
                position 1;
                description "SONET/SDH compliant code S-64.2a";
            }
            bit xssh-s-64-2b {
                position 2;
                description "SONET/SDH compliant code s-64.2b";
            }
            bit xssh-s-64-3a {
                position 3;
                description "SONET/SDH compliant code S-64.3a";
            }
            bit xssh-s-64-3b {
                position 4;
                description "SONET/SDH compliant code S-64.3b";
            }
            bit xssh-s-64-5a {
                position 5;
                description "SONET/SDH compliant code S-64.5a";
            }
            bit xssh-s-64-56 {
                position 6;
                description "SONET/SDH compliant code S-64.5b";
            }
        }
        description "type definition for DDM_CMM_TRANS_XFP_SONET_SHORT_HAUL_T";
    }

    typedef  ddm_cmm_trans_xfp_sonet_long_haul_t {
        type bits {
            bit xslh-l-64-l {
                position 0;
                description "SONET/SDH compliant code L-64.1";
            }
            bit xslh-l-64-2a {
                position 1;
                description "SONET/SDH compliant code L-64.2a";
            }
            bit xslh-l-64-2b {
                position 2;
                description "SONET/SDH compliant code L-64.2b";
            }
            bit xslh-l-64-2c {
                position 3;
                description "SONET/SDH compliant code L-64.2c";
            }
            bit xslh-l-64-3 {
                position 4;
                description "SONET/SDH compliant code L-64.3";
            }
            bit xlsh-l-g959-1-p1l1-2d2 {
                position 5;
                description "SONET/SDH compliant code G.959.1 P1L1-2D2";
            }
        }
        description "type definition for DDM_CMM_TRANS_XFP_SONET_LONG_HAUL_T";
    }

    typedef  ddm_cmm_trans_xfp_sonet_very_long_haul_t {
        type bits {
            bit xsvh-v-64-2a {
                position 0;
                description "SONET/SDH compliant code V-64.2a";
            }
            bit xsvh-v-64-2b {
                position 1;
                description "SONET/SDH compliant code V-64.2b";
            }
            bit xsvh-v-64-3 {
                position 2;
                description "SONET/SDH compliant code V-64.3";
            }
        }
        description "type definition for DDM_CMM_TRANS_XFP_SONET_VERY_LONG_HAUL_T";
    }

    typedef  ddm_cmm_trans_encoding_t {
        type enumeration {
            enum enc-unspecified {
                value 1;
                description "enc-unspecified";
            }
            enum enc-8b-or-10b {
                value 2;
                description "enc-8b-or-10b";
            }
            enum enc-4b-or-5b {
                value 3;
                description "enc-4b-or-5b";
            }
            enum enc-nrz {
                value 4;
                description "enc-nrz";
            }
            enum enc-manchester {
                value 5;
                description "enc-manchester";
            }
            enum enc-sonet-scrambled {
                value 6;
                description "enc-sonet-scrambled";
            }
            enum enc-64b-or-66b {
                value 7;
                description "enc-64b-or-66b";
            }
            enum enc-256b-or-257b {
                value 8;
                description "enc-256b-or-257b";
            }
            enum enc-pam4 {
                value 9;
                description "enc-pam4";
            }
            enum enc-reserved {
                value 10;
                description "enc-reserved";
            }
        }
        description "type definition for DDM_CMM_TRANS_ENCODING_T";
    }

    typedef  ddm_cmm_trans_xfp_encoding_t {
        type bits {
            bit enc-reserved0 {
                position 0;
                description "XFP encoding reserved 0";
            }
            bit enc-reserved1 {
                position 1;
                description "XFP encoding reserved 1";
            }
            bit enc-reserved2 {
                position 2;
                description "XFP encoding reserved 2";
            }
            bit enc-rz {
                position 3;
                description "XFP encoding RZ";
            }
            bit enc-nrz {
                position 4;
                description "XFP encoding NRZ";
            }
            bit enc-sonet-scrambled {
                position 5;
                description "XFP encoding SONET Scrambled";
            }
            bit enc-8b-10b {
                position 6;
                description "XFP encoding 8b/10b";
            }
            bit enc-64b-66b {
                position 7;
                description "XFP encoding 64b/66b";
            }
        }
        description "type definition for DDM_CMM_TRANS_XFP_ENCODING_T";
    }

    typedef  ddm_cmm_trans_ddm_support_t {
        type enumeration {
            enum yes {
                value 1;
                description "DDM is supported";
            }
            enum no {
                value 2;
                description "DDM is not supported";
            }
            enum unknown {
                value 3;
                description "DDM support unknown";
            }
        }
        description "type definition for DDM_CMM_TRANS_DDM_SUPPORT_T";
    }

    typedef  ddm_cmm_trans_sfp_options_implemented_t {
        type bits {
            bit reserved {
                position 0;
                description "reserved";
            }
            bit power-level3 {
                position 1;
                description "power-level3";
            }
            bit paging {
                position 2;
                description "paging";
            }
            bit internal-retimer-or-cdr {
                position 3;
                description "internal-retimer-or-cdr";
            }
            bit cooled-laser-transmitter {
                position 4;
                description "cooled-laser-transmitter";
            }
            bit power-level2 {
                position 5;
                description "power-level2";
            }
            bit power-level1 {
                position 6;
                description "power-level1";
            }
            bit linear-receiver-output {
                position 7;
                description "linear-receiver-output";
            }
            bit receiver-decision-threshold {
                position 8;
                description "receiver-decision-threshold";
            }
            bit transmitter-wavelength-or-tunable-frequency {
                position 9;
                description "transmitter-wavelength-or-tunable-frequency";
            }
            bit rate-select {
                position 10;
                description "rate-select";
            }
            bit tx-disable {
                position 11;
                description "tx-disable";
            }
            bit tx-fault {
                position 12;
                description "tx-fault";
            }
            bit rx-loss-of-signal {
                position 13;
                description "rx-loss-of-signal";
            }
            bit null {
                position 31;
                description "NULL";
            }
        }
        description "type definition for DDM_CMM_TRANS_SFP_OPTIONS_IMPLEMENTED_T";
    }

    typedef  ddm_cmm_trans_qsfp_options_implemented_t {
        type bits {
            bit reserved {
                position 0;
                description "reserved";
            }
            bit tx-inputequalization-auto-adaptive {
                position 1;
                description "tx-inputequalization-auto-adaptive";
            }
            bit tx-inputequalization-fixed-programmable {
                position 2;
                description "tx-inputequalization-fixed-programmable";
            }
            bit tx-outputemphasis-fixed-programmable {
                position 3;
                description "tx-outputemphasis-fixed-programmable";
            }
            bit tx-outputamplitude-fixed-programmable {
                position 4;
                description "tx-outputamplitude-fixed-programmable";
            }
            bit tx-cdr-on-or-off-controllable {
                position 5;
                description "tx-cdr-on-or-off-controllable";
            }
            bit tx-cdr-on-or-off-fixed {
                position 6;
                description "tx-cdr-on-or-off-fixed";
            }
            bit rx-cdr-on-or-off-controllable {
                position 7;
                description "rx-cdr-on-or-off-controllable";
            }
            bit rx-cdr-on-or-off-fixed {
                position 8;
                description "rx-cdr-on-or-off-fixed";
            }
            bit tx-cdr-lossoflock {
                position 9;
                description "tx-cdr-lossoflock";
            }
            bit rx-cdr-lossoflock {
                position 10;
                description "rx-cdr-lossoflock";
            }
            bit rx-squelch-disable {
                position 11;
                description "rx-squelch-disable";
            }
            bit rx-output-disable {
                position 12;
                description "rx-output-disable";
            }
            bit tx-squelch-disable {
                position 13;
                description "tx-squelch-disable";
            }
            bit tx-squelch {
                position 14;
                description "tx-squelch";
            }
            bit page2-provided {
                position 15;
                description "page2-provided";
            }
            bit page1-provided {
                position 16;
                description "page1-provided";
            }
            bit rateselect-controllable {
                position 17;
                description "rateselect-controllable";
            }
            bit rateselect-fixed {
                position 18;
                description "rateselect-fixed";
            }
            bit tx-disable {
                position 19;
                description "tx-disable";
            }
            bit tx-fault {
                position 20;
                description "tx-fault";
            }
            bit tx-squelch-to-reduce-pave {
                position 21;
                description "tx-squelch-to-reduce-pave";
            }
            bit tx-squelch-to-reduce-oma {
                position 22;
                description "tx-squelch-to-reduce-oma";
            }
            bit tx-loss-of-signal {
                position 23;
                description "tx-loss-of-signal";
            }
            bit null {
                position 31;
                description "NULL";
            }
        }
        description "type definition for DDM_CMM_TRANS_QSFP_OPTIONS_IMPLEMENTED_T";
    }

    typedef  ddm_cmm_trans_xfp_options_implemented_t {
        type bits {
            bit xfp-vps {
                position 0;
                description "XFP optional variable power supply";
            }
            bit xfp_tx-disable {
                position 1;
                description "XFP soft TX disable support";
            }
            bit xfp-p-down {
                position 2;
                description "XFP soft power down support";
            }
            bit xfp-vps-lv {
                position 3;
                description "XFP VPS low voltage regulator mode";
            }
            bit xfp-vps-bypass {
                position 4;
                description "XFP VPS bypass mode";
            }
            bit xfp-active-fec {
                position 5;
                description "XFP active FEC control";
            }
            bit xfp-wavelength-tunability {
                position 6;
                description "XFP wavelength tunability";
            }
            bit xfp-cmu {
                position 7;
                description "XFP Clock Multiplier Unit mode";
            }
        }
        description "type definition for DDM_CMM_TRANS_XFP_OPTIONS_IMPLEMENTED_T";
    }

    typedef  ddm_cmm_trans_xfp_voltage_aux_monitor_t {
        type bits {
            bit xfp-vcc-5 {
                position 0;
                description "XFP auxiliary monitor for VCC5";
            }
            bit xfp-vcc-3 {
                position 1;
                description "XFP auxiliary monitor for VCC3";
            }
            bit xfp-vcc-2 {
                position 2;
                description "XFP auxiliary monitor for VCC2";
            }
        }
        description "type definition for DDM_CMM_TRANS_XFP_VOLTAGE_AUX_MONITOR_T";
    }

}

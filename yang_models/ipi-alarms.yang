/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-alarms.yang
*
*/

module ipi-alarms {

    yang-version 1.1;

    namespace   "http://www.ipinfusion.com/yang/ocnos/ipi-alarms";

    prefix "ipi-alarms";

    import ipi-platform {
        prefix ipi-platform;
        revision-date 2022-02-18;
    }

    import ipi-alarms-types {
        prefix ipi-alarms-types;
        revision-date 2021-09-03;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for operational state data related to alarms that the device
                is reporting";


    revision "2021-09-03" {
        description "Update descriptions of attribute";
        reference " 0.2.0.";
    }

    revision "2021-07-28" {
        description "Initial Version";
        reference " 0.1.0.";
    }

    grouping alarm-state {
        description
            "Operational state data for device alarms";
        leaf id  {
            type  string {
                length "1..1965";
            }
            description "Unique ID for the alarm";
        } // END of id definition.

        leaf resource  {
            type  string {
                length "1..1965";
            }
            description "The item that is under alarm within the device";
        } // END of resource definition.

        leaf text  {
            type  string {
                length "1..1965";
            }
            description "The string used to inform operators about the alarm";
        } // END of text definition.

        leaf time-created  {
            type  uint64;
            description "The time at which the alarm was raised by the system. This value is
                        expressed relative to the Unix Epoch";
        } // END of time-created definition.

        leaf alarm-reported-timestamp  {
            type  ipi-alarms-types:alarm_date_time_t {
                length "1..1965";
            }
            description "The date-time at which the alarm was raised by the system";
        } // END of alarm-reported-timestamp definition.

        leaf alarm-severity  {
            type  ipi-alarms-types:alarm_severity_t;
            description "The severity level indicating the criticality and impact of the alarm";
        } // END of alarm-severity definition.

        leaf type-id  {
            type  ipi-alarms-types:alarm_type_id_t;
            description "The abbreviated name of the alarm";
        } // END of type-id definition.

    } // END of alarm-state definition.
    grouping alarm-list-top {
        description
            "Top-level grouping for device alarms";

        list alarm {
            key "id";
            config false;
            description
                "List of alarms, keyed by a unique id";
            leaf id  {
                type  leafref {
                    path  "../state/id";
                }
                description "References the unique alarm id";
            } // END of id definition.

            container state {
                config false;
                description
                    "Operational state data for a device alarm";
                uses alarm-state;
            } // END of state-container definition.
        } // End of alarm-list
    } // END of alarm-list-top definition.

    grouping  alarms-grouping {
    description
        "Top-level container for operational state data related to alarms that
                the device is reporting";
    container alarms {
        description
            "Top-level container for operational state data related to alarms that
                    the device is reporting";
        uses alarm-list-top;
    } // END of alarms-container definition.
    } // END of alarms-grouping definition.

    grouping  component-alarm-grouping {
    description
        "Container for component alarm";
    container component-alarm {
        config false;
        description
            "Container for component alarm";
        leaf equipment-failure  {
            type  boolean;
            description "If trueCOMMA the hardware indicates that the component's physical
                        equipment";
        } // END of equipment-failure definition.

    } // END of component-alarm-container definition.
    } // END of component-alarm-grouping definition.

    uses alarms-grouping;
    augment /ipi-platform:components/ipi-platform:component/ipi-platform:state {
        description
            "Container for component alarm";
        uses component-alarm-grouping;
    }


    notification alarm {

        description "Notify the event of an alarm raised.";

        // eventClass "STATE";
        leaf id {
            type  string;
        description
            "References the unique alarm id";
        }

        leaf resource {
            type  string;
        description
            "The item that is under alarm within the device";
        }

        leaf text {
            type  string;
        description
            "The string used to inform operators about the alarm";
        }

        leaf time-created {
            type  uint64;
        description
            "The time at which the alarm was raised by the system. This value is
                    expressed relative to the Unix Epoch";
        }

        leaf alarm-reported-timestamp {
            type ipi-alarms-types:alarm_date_time_t;
        description
            "The date-time at which the alarm was raised by the system";
        }

        leaf alarm-severity {
            type ipi-alarms-types:alarm_severity_t;
        description
            "The severity level indicating the criticality and impact of the alarm";
        }

        leaf type-id {
            type ipi-alarms-types:alarm_type_id_t;
        description
            "The abbreviated name of the alarm";
        }
    }

}

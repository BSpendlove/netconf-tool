/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-interface.yang
*
*/

module ipi-interface {

    yang-version 1.1;

    namespace   "http://www.ipinfusion.com/yang/ocnos/ipi-interface";

    prefix "ipi-interface";

    import cml-data-types {
        prefix cml-data-types;
        revision-date 2022-04-04;
    }

    import ietf-yang-types {
        prefix yang;
        revision-date 2013-07-15;
    }

    import ipi-if-types {
        prefix ipi-if-types;
        revision-date 2021-11-10;
    }

    import ipi-network-instance {
        prefix ipi-network-instance;
        revision-date 2021-11-10;
    }

    import ipi-vrf {
        prefix ipi-vrf;
        revision-date 2021-09-03;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for interface object";


    revision "2022-04-05" {
        description "Add dependent object between interface and NDD objects";
        reference " 0.9.3.";
    }

    revision "2021-12-15" {
        description "Add if-feature on dependent object between interface and DHCP snooping objects";
        reference " 0.9.2.";
    }

    revision "2021-12-07" {
        description "Add dependent object for between interface and DHCP snooping objects";
        reference " 0.9.1.";
    }

    revision "2021-11-29" {
        description "Leaf port-breakout moved to its own datamodel ipi-port-breakout.";
        reference " 0.9.0.";
    }

    revision "2021-11-16" {
        description "SKU compilation fixes";
        reference " 0.8.1.";
    }

    revision "2021-11-10" {
        description "Add dependentObject when operation is delete to remove module ipi-cross-connect:cross-connect before than interfaces module.";
        reference " 0.8.0.";
    }

    revision "2021-11-08" {
        description "Fix the when tags related to the intra-domain peer configuration";
        reference " 0.7.1.";
    }

    revision "2021-10-20" {
        description "Removed dot1q-ether-type dependency from LAG interface having mlag-id";
        reference " 0.7.0.";
    }

    revision "2021-09-29" {
        description "Updated attribute dot1q-ether-type description, added length and pattern tag";
        reference " 0.6.5.";
    }

    revision "2021-09-28" {
        description "Changed interface name and CLI for ethertype configuration
                       Modified when tags dependent on MCEC configurations
        ";
        reference " 0.6.4.";
    }

    revision "2021-09-20" {
        description "Changed interface name description to add subinterface details";
        reference " 0.6.3.";
    }

    revision "2021-09-10" {
        description "Changed max MTU from 65536 to 65535";
        reference " 0.6.2.";
    }

    revision "2021-09-01" {
        description "Changed name of attribute enabled and switchport-status to shutdown and enable-switchport and data-types from CML_BOOL_T to CML_EMPTY_T.";
        reference " 0.6.1.";
    }

    revision "2021-07-15" {
        description "Added new attribute switchport-protected.";
        reference " 0.6.0.";
    }

    revision "2021-07-07" {
        description "Add a specific condition in the triggers for MTU and Ethertype related to the mlag IDL interface.";
        reference " 0.5.4.";
    }

    revision "2021-06-29" {
        description "Add a trigger to remove mtu from interface when it is a mlag IDL.";
        reference " 0.5.3.";
    }

    revision "2021-06-24" {
        description "Add a trigger to remove dot1q-ether-type from interface when it is a mlag IDL.";
        reference " 0.5.2.";
    }

    revision "2021-06-14" {
        description "Moved attibute dot1q-ether-type from extended interface module to base interface module.";
        reference " 0.5.1.";
    }

    revision "2021-03-16" {
        description "Combined switchport with switchport-status and updated when tags for sub-interface remodelling.";
        reference " 0.5.0.";
    }

    revision "2021-03-01" {
        description "Changed data-types of attribute mtu and ifindex to CML_UINT32_T";
        reference " 0.4.0.";
    }

    revision "2020-12-15" {
        description "Change to have data-types in lower case instead of camel case";
        reference " 0.3.0.";
    }

    revision "2020-11-13" {
        description "For attributes using string data type, changed range to length";
        reference " 0.2.0.";
    }

    revision "2020-07-15" {
        description "Initial Version. Openconfig Yang model : https://github.com/openconfig/public/blob/master/release/models/interfaces/openconfig-interfaces.yang";
        reference " 0.1.0.";
    }

    grouping interface-common-config {
        description
            "Configuration data data nodes common to physical interfaces and
                        subinterfaces";
        leaf description  {
            type  cml-data-types:cml_line_t {
                length "1..128";
            }
            description "Use this attribute to set description for the interface";
        } // END of description definition.

        leaf shutdown  {
            type  empty;
            description "Use this attribute to enable the selected interface.
                        This leaf contains the configured, desired state of the interface.
                        The testing(3) state indicates that no operational packets can be
                        passed.
                        When a managed system initializes, all interfaces start with
                        ifAdminStatus in the down(2) state.
                        As a result of either explicit management action or per configuration
                        information retained by the managed system,
                        ifAdminStatus is then changed to either the up(1) or testing(3)
                        states (or remains in the down(2) state).";
        } // END of shutdown definition.

    } // END of interface-common-config definition.
    grouping interface-phys-config {
        description
            "Configuration data for physical interfaces";
        leaf name  {
            type  string {
                length "1..33";
                pattern "[^?' =,>|]+";
            }
            description "The textual name of the interface. The value of this
                        object should
                        be the name of the interface as assigned by the local device and
                        should be suitable for use in commands entered at the device's
                        `console'. This might be a text name, such as `le0' or a simple
                        port number, such as `1', depending on the interface naming syntax
                        of the device. If several entries in the ifTable together represent
                        a single interface as named by the device, then each will have the
                        same value of name . Note that for an agent which responds to SNMP
                        queries concerning an interface on some other (proxied) device,
                        then the value of name for such an interface is the proxied
                        device's local name for it. If there is no local name, or this
                        object is otherwise not applicable, then this object contains a
                        zero-length string. To configure a subinterface, use the name of
                        the base interface followed by a dot and a number in the range
                        of 1-2000 (eg: xe1.1).";
        } // END of name definition.

        leaf enable-switchport  {
            type  empty;
            description "This attribute is used to set the mode of the Hybrid Switch Router
                        feature to switched only.All interfaces are configured routed by
                        default";
        } // END of enable-switchport definition.

        leaf vrf-name  {
            if-feature feature-list:HAVE_VRF;
            type  leafref {
                path  "/ipi-network-instance:network-instances/ipi-network-instance:network-instance/ipi-vrf:vrf/ipi-vrf:config/ipi-vrf:vrf-name";
            }
            description "This attribute is used to associates an interface with a VRF";
        } // END of vrf-name definition.

        leaf vr-name  {
            if-feature feature-list:HAVE_VR;
            type  string {
                length "1..1965";
                pattern "[^?' =,>|]+";
            }
            description "This attribute is used to associates an interface with a VR";
        } // END of vr-name definition.

        leaf type  {
            type  ipi-if-types:if_iana_if_type_t;
            description "The type of the interface.
                        When an interface entry is created, a server MAY
                        initialize the type leaf with a valid value, e.g., if it
                        is possible to derive the type from the name of the
                        interface.";
        } // END of type definition.

        leaf mtu  {
            type  uint32 {
                 range "64..65535"  {
                    description "64..65535:MTU in bytes: (64-9416) for L2 packet (576-9216) for L3 IPv4
                            packet (1280-9216) for L3 IPv6 packet (576-65535) for IPv4 packet and
                            (1280-65535) for IPv6 packet on loopback interface";
                 }
            }
            description "This attribute is used to set mtu value to interface.The size of the
                        largest packet which can be sent/received on the interface, specified
                        in octets.  For interfaces that are used for transmitting network
                        datagrams, this is the size of the largest network datagram that can
                        be sent on the interface.";
        } // END of mtu definition.

        leaf dot1ad-ether-type  {
            if-feature feature-list:HAVE_VLAN_STACK;
            if-feature feature-list:NOT_HAVE_SWFWDR;
            type  string {
                length "6";
                pattern "0[xX][0-9a-fA-F]+";
            }
            description "This attribute is used to configure the ethertype value for the
                        interface in the format 0xhhhh. Currently supported values are 0x8100
                        (default) or 0x88a8 or 0x9100 or 0x9200.";
        } // END of dot1ad-ether-type definition.

        leaf domain-fastflush-config  {
            if-feature feature-list:HAVE_DNX;
            type  empty;
            description "Attribute to change domain fastflush value";
        } // END of domain-fastflush-config definition.

        leaf protected-port  {
            // when " !ipi-mlag:mlag-aggregation/config/mlag-id ";
            if-feature feature-list:HAVE_DUNE;
            type  ipi-if-types:if_protected_port_type_t;
            default "promiscuous";
            description "Attribute to change port protectedtype value";
        } // END of protected-port definition.

        leaf domain-forward-config  {
            // when " !ipi-mlag:mlag-aggregation/config/mlag-id ";
            if-feature feature-list:HAVE_DUNE;
            type  empty;
            description "Attribute to change domain forward value";
        } // END of domain-forward-config definition.

        uses interface-common-config;
    } // END of interface-phys-config definition.
    grouping interface-loopback-config {
        description
            "Interface Loopback Config";
        leaf if-loopback  {
            type  ipi-if-types:if_loopback_dir_type_t;
            mandatory true;
            description "This attribute is used to enable port loopback";
        } // END of if-loopback definition.

        leaf if-loopback-level  {
            type  ipi-if-types:if_loopback_type_t;
            mandatory true;
            description "This attribute is used to enable port loopback";
        } // END of if-loopback-level definition.

    } // END of interface-loopback-config definition.
    grouping interface-common-state {
        description
            "Operational state data (in addition to intended configuration) at the
                        global level for this interface";
        leaf ifindex  {
            type  uint32;
            config false;
            description "System assigned number for each interface. A unique value,
                        greater
                        than zero, for each interface.It is recommended that values are
                        assigned contiguously starting from 1.The value for each interface
                        sub-layer must remain constant at least from one re-initialization
                        of the entity's network management system to the next
                        re-initialization.";
        } // END of ifindex definition.

        leaf admin-status  {
            type  ipi-if-types:if_interface_admin_status_t;
            config false;
            description "The desired state of the interface. It reflects the
                        administrative
                        state as set by enabling or disabling the interface.";
        } // END of admin-status definition.

        leaf oper-status  {
            type  ipi-if-types:if_interface_oper_status_t;
            config false;
            description "The current operational state of the interface.  The
                        testing(3) state indicates that no operational packets can
                        be passed.  If admin-status is down(2) then oper-status
                        should be down(2).  If admin-status is changed to up(1)
                        then oper-status should change to up(1) if the interface is
                        ready to transmit and receive network traffic; it should
                        change to dormant(5) if the interface is waiting for
                        external actions (such as a serial line waiting for an
                        incoming connection); it should remain in the down(2) state
                        if and only if there is a fault that prevents it from going
                        to the up(1) state; it should remain in the notPresent(6)
                        state if the interface has missing (typically, hardware)
                        components.";
        } // END of oper-status definition.

        leaf last-change  {
            type  yang:timeticks;
            config false;
            description "The value of sysUpTime at the time the interface entered
                        its current operational state.If the current state was
                        entered prior to the last re-initialization of the local
                        network management subsystem then this object contains a
                        zero value";
        } // END of last-change definition.

        leaf logical  {
            type  boolean;
            config false;
            description "When set to true, the interface is a logical interface
                        which does not have an associated physical port or channel on the
                        system";
        } // END of logical definition.

    } // END of interface-common-state definition.
    grouping interface-counters-state {
        description
            "Operational state representing interface counters and statistics.";
        container counters {
            config false;
            description
                "A collection of interface-related statistics objects";
            leaf in-octets  {
                type  yang:counter64;
                description "The total number of octets received on the interface,
                            including
                            framing characters. Discontinuities in the value of this counter
                            can occur at re-initialization of the management system,
                            and at other times as indicated by the value of 'last-clear'.";
            } // END of in-octets definition.

            leaf in-pkts  {
                type  yang:counter64;
                description "The total number of packets received on the interface,
                            including all unicast, multicast, broadcast and bad packets etc.";
            } // END of in-pkts definition.

            leaf in-unicast-pkts  {
                if-feature feature-list:HAVE_BROADCOM;
                if-feature feature-list:HAVE_HAL;
                if-feature feature-list:NOT_HAVE_SWFWDR;
                type  yang:counter64;
                description "The number of packets, delivered by this sub-layer to a
                            higher (sub-)layer, which were not addressed to a multicast
                            or broadcast address at this sub-layer.
                            Discontinuities in the value of this counter can occur at
                            re-initialization of the management system, and at other
                            times as indicated by the value of
                            ifCounterDiscontinuityTime.";
            } // END of in-unicast-pkts definition.

            leaf in-broadcast-pkts  {
                if-feature feature-list:HAVE_BROADCOM;
                if-feature feature-list:HAVE_HAL;
                if-feature feature-list:NOT_HAVE_SWFWDR;
                type  yang:counter64;
                description "The number of packets, delivered by this sub-layer to a
                            higher (sub-)layer, that were addressed to a broadcast
                            address at this sub-layer.
                            Discontinuities in the value of this counter can occur
                            at re-initialization of the management system, and at
                            other times as indicated by the value of
                            'last-clear'.";
            } // END of in-broadcast-pkts definition.

            leaf in-multicast-pkts  {
                type  yang:counter64;
                description "The number of packets, delivered by this sub-layer to a
                            higher (sub-)layer, that were addressed to a multicast
                            address at this sub-layer.  For a MAC-layer protocol,
                            this includes both Group and Functional addresses.
                            Discontinuities in the value of this counter can occur
                            at re-initialization of the management system, and at
                            other times as indicated by the value of
                            'last-clear'.";
            } // END of in-multicast-pkts definition.

            leaf in-discards  {
                type  yang:counter64;
                description "The number of inbound packets that were chosen to be
                            discarded even though no errors had been detected to
                            prevent their being deliverable to a higher-layer
                            protocol.  One possible reason for discarding such a
                            packet could be to free up buffer space.
                            Discontinuities in the value of this counter can occur
                            at re-initialization of the management system, and at
                            other times as indicated by the value of
                            'last-clear'";
            } // END of in-discards definition.

            leaf in-errors  {
                type  yang:counter64;
                description "For packet-oriented interfaces, the number of inbound
                            packets that contained errors preventing them from being
                            deliverable to a higher-layer protocol.  For character-
                            oriented or fixed-length interfaces, the number of
                            inbound transmission units that contained errors
                            preventing them from being deliverable to a higher-layer
                            protocol. Discontinuities in the value of this counter can occur
                            at re-initialization of the management system, and at
                            other times as indicated by the value of
                            'last-clear'";
            } // END of in-errors definition.

            leaf in-fcs-errors  {
                if-feature feature-list:HAVE_BROADCOM;
                if-feature feature-list:HAVE_HAL;
                if-feature feature-list:NOT_HAVE_SWFWDR;
                type  yang:counter64;
                description "Number of received packets which had errors in the
                            frame check sequence (FCS), i.e., framing errors.
                            Discontinuities in the value of this counter can occur
                            when the device is re-initialization as indicated by the
                            value of 'last-clear'.";
            } // END of in-fcs-errors definition.

            leaf out-octets  {
                type  yang:counter64;
                description "The total number of octets transmitted out of the
                            interface, including framing characters.
                            Discontinuities in the value of this counter can occur
                            at re-initialization of the management system, and at
                            other times as indicated by the value of
                            'last-clear'.";
            } // END of out-octets definition.

            leaf out-pkts  {
                type  yang:counter64;
                description "The total number of packets transmitted out of the
                            interface, including all unicast, multicast, broadcast,
                            and bad packets etc.";
            } // END of out-pkts definition.

            leaf out-unicast-pkts  {
                if-feature feature-list:HAVE_BROADCOM;
                if-feature feature-list:HAVE_HAL;
                if-feature feature-list:NOT_HAVE_SWFWDR;
                type  yang:counter64;
                description "The total number of packets that higher-level protocols
                            requested be transmitted, and which were not addressed to a
                            multicast or broadcast address at this sub-layer, including
                            those that were discarded or not sent.
                            Discontinuities in the value of this counter can occur at
                            re-initialization of the management system, and at other
                            times as indicated by the value of
                            ifCounterDiscontinuityTime.";
            } // END of out-unicast-pkts definition.

            leaf out-broadcast-pkts  {
                if-feature feature-list:HAVE_BROADCOM;
                if-feature feature-list:HAVE_HAL;
                if-feature feature-list:NOT_HAVE_SWFWDR;
                type  yang:counter64;
                description "The total number of packets that higher-level protocols
                            requested be transmitted, and that were addressed to a
                            broadcast address at this sub-layer, including those
                            that were discarded or not sent.
                            Discontinuities in the value of this counter can occur
                            at re-initialization of the management system, and at
                            other times as indicated by the value of
                            'last-clear'";
            } // END of out-broadcast-pkts definition.

            leaf out-multicast-pkts  {
                if-feature feature-list:HAVE_BROADCOM;
                if-feature feature-list:HAVE_HAL;
                if-feature feature-list:NOT_HAVE_SWFWDR;
                type  yang:counter64;
                description "The total number of packets that higher-level protocols
                            requested be transmitted, and which were addressed to a
                            multicast address at this sub-layer, including those that
                            were discarded or not sent.  For a MAC layer protocol, this
                            includes both Group and Functional addresses.
                            Discontinuities in the value of this counter can occur at
                            re-initialization of the management system, and at other
                            times as indicated by the value of
                            ifCounterDiscontinuityTime.";
            } // END of out-multicast-pkts definition.

            leaf out-discards  {
                type  yang:counter64;
                description "The number of outbound packets that were chosen to be
                            discarded even though no errors had been detected to
                            prevent their being transmitted.  One possible reason
                            for discarding such a packet could be to free up buffer
                            space.
                            Discontinuities in the value of this counter can occur
                            at re-initialization of the management system, and at
                            other times as indicated by the value of
                            'last-clear'.";
            } // END of out-discards definition.

            leaf out-errors  {
                type  yang:counter64;
                description "For packet-oriented interfaces, the number of outbound
                            packets that could not be transmitted because of errors.
                            For character-oriented or fixed-length interfaces, the
                            number of outbound transmission units that could not be
                            transmitted because of errors.
                            Discontinuities in the value of this counter can occur
                            at re-initialization of the management system, and at
                            other times as indicated by the value of
                            'last-clear'.";
            } // END of out-errors definition.

            leaf last-clear  {
                type  ipi-if-types:if_last_clear_time_t {
                    length "1..1965";
                }
                description "This Object describes the last counter clear";
            } // END of last-clear definition.

        } // END of counters-container definition.
    } // END of interface-counters-state definition.

    grouping  interfaces-grouping {
    description
        "Top level container for interfaces, including configuration and state
                data";
    container interfaces {
        description
            "Top level container for interfaces, including configuration and state
                    data";

        list interface {
            key "name";
            description
                "The list of named interfaces on the device.";
            leaf name  {
                type  leafref {
                    path  "../config/name";
                }
                description "The textual name of the interface. The value of this
                            object should
                            be the name of the interface as assigned by the local device and
                            should be suitable for use in commands entered at the device's
                            `console'. This might be a text name, such as `le0' or a simple
                            port number, such as `1', depending on the interface naming syntax
                            of the device. If several entries in the ifTable together represent
                            a single interface as named by the device, then each will have the
                            same value of name. Note that for an agent which responds to SNMP
                            queries concerning an interface on some other (proxied) device,
                            then the value of name for such an interface is the proxied
                            device's local name for it. If there is no local name, or this
                            object is otherwise not applicable, then this object contains a
                            zero-length string.";
            } // END of name definition.

            container config {
                description
                    "Configurable items at the global, physical interface level";
                uses interface-phys-config;
            } // END of config-container definition.
            container state {
                config false;
                description
                    "Operational state data at the global interface level";
                uses interface-phys-config;
                uses interface-common-state;
                uses interface-counters-state;
            } // END of state-container definition.
            container interface-loopback {
                description
                    "Configurable items at the global, physical interface level";
                container config {
                    presence "if-loopback";
                    description
                        "Operational state data at the global interface level";
                    uses interface-loopback-config;
                } // END of config-container definition.
                container state {
                    config false;
                    description
                        "Operational state data at the global interface level";
                    uses interface-loopback-config;
                } // END of state-container definition.
            } // END of interface-loopback-container definition.
        } // End of interface-list
    } // END of interfaces-container definition.
    } // END of interfaces-grouping definition.

    uses interfaces-grouping;

    rpc clear-interface-counters {
        description "Use clear-interface-counters to clear all interface counters, to clear
                    counters for a specific interface pass the interface name . E.g
                    clear-interface-counters name=eth1";
        input  {
            leaf name  {
                type string;
                mandatory true;
                description "Name of the interface to clear counters for. Specify NULL to clear
                            counters for all interfaces";
            }
        }
    }

    notification interface-link-state-change-notification {

        description "A linkDown specifies that one of the communication links is about to enter the down state from some other state (but not from the notPresent state).  This other state is indicated by the included value of ifOperStatus. A linkUp trap signifies that one of communication links left the down state and transitioned into some other state (but not into the notPresent state).  This other state is indicated by the included value of ifOperStatus. Severity level is CRITICAL for link state Down and MINOR for link state Up..";

        // eventClass "STATE";
        leaf name {
            type  string;
        description
            "The textual name of the interface. The value of this
                    object should
                    be the name of the interface as assigned by the local device and
                    should be suitable for use in commands entered at the device's
                    `console'. This might be a text name, such as `le0' or a simple
                    port number, such as `1', depending on the interface naming syntax
                    of the device. If several entries in the ifTable together represent
                    a single interface as named by the device, then each will have the
                    same value of name. Note that for an agent which responds to SNMP
                    queries concerning an interface on some other (proxied) device,
                    then the value of name for such an interface is the proxied
                    device's local name for it. If there is no local name, or this
                    object is otherwise not applicable, then this object contains a
                    zero-length string.";
        }

        leaf oper-status {
            type ipi-if-types:if_interface_oper_status_t;
        description
            "The current operational state of the interface.  The
                    testing(3) state indicates that no operational packets can
                    be passed.  If admin-status is down(2) then oper-status
                    should be down(2).  If admin-status is changed to up(1)
                    then oper-status should change to up(1) if the interface is
                    ready to transmit and receive network traffic; it should
                    change to dormant(5) if the interface is waiting for
                    external actions (such as a serial line waiting for an
                    incoming connection); it should remain in the down(2) state
                    if and only if there is a fault that prevents it from going
                    to the up(1) state; it should remain in the notPresent(6)
                    state if the interface has missing (typically, hardware)
                    components.";
        }
    }

}

/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-igp-te.yang
*
*/

module ipi-igp-te {

    yang-version 1.1;

    namespace   "http://www.ipinfusion.com/yang/ocnos/ipi-igp-te";

    prefix "ipi-igp-te";

    import ipi-interface {
        prefix ipi-interface;
        revision-date 2022-04-05;
    }

    import cml-data-types {
        prefix cml-data-types;
        revision-date 2022-04-04;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for IGP-TE";


    revision "2021-10-21" {
        description "Added IGP-TE dynamic cli with TWAMP configuration";
        reference " 0.1.4.";
    }

    revision "2021-09-01" {
        description "Changed base interface module's switchport attribute name and the datatype from bool to empty";
        reference " 0.1.3.";
    }

    revision "2021-08-08" {
        description "Fix for IGP-TE feature data model hierarchy changes";
        reference " 0.1.2.";
    }

    revision "2021-08-06" {
        description "Fix for IGP-TE feature Netconf issues";
        reference " 0.1.1.";
    }

    revision "2021-07-26" {
        description "IGP-TE feature support";
        reference " 0.1.0.";
    }

    grouping igp-te-config {
        description
            "Grouping for IGP TE configuration on interface";
        leaf delay  {
            type  uint32 {
                 range "1..16777215"  {
                    description "1..16777215:Value in microseconds";
                 }
            }
            units "microseconds";
            description "Use this attribute to specify a unidirectional, link delay value for
                        the interface";
        } // END of delay definition.

        leaf delay-variation  {
            type  uint32 {
                 range "0..16777215"  {
                    description "0..16777215:Value in microseconds";
                 }
            }
            units "microseconds";
            description "Use this attribute to specify a unidirectional, link delay variation
                        value for the interface";
        } // END of delay-variation definition.

        leaf loss-percentage  {
            type  decimal64 {
                 fraction-digits 6;            }
            description "Use this attribute to specify a unidirectional, link loss value for
                        the interface";
        } // END of loss-percentage definition.

    } // END of igp-te-config definition.
    grouping loss-dynamic-config {
        description
            "loss-dynamic-config";
        leaf loss-dynamic  {
            when " /ipi-igp-te:igp-te/ipi-igp-te:interfaces/ipi-igp-te:interface/ipi-igp-te:uni-link/ipi-igp-te:twamp-session-parameters/ipi-igp-te:twamp-session-parameter/ipi-igp-te:config/ipi-igp-te:delay-dynamic-twamp ";
            type  empty;
            description "Use this attribute to specify a loss percentage value dynamically for
                        the interface";
        } // END of loss-dynamic definition.

    } // END of loss-dynamic-config definition.
    grouping twamp-session-parameters-config {
        description
            "TWAMP session parameters";
        leaf delay-dynamic-twamp  {
            type  empty;
            description "Use this command to start the delay measurement for the interface";
        } // END of delay-dynamic-twamp definition.

        leaf reflector-ip  {
            type  cml-data-types:cml_hostpname_t;
            description "";
        } // END of reflector-ip definition.

        leaf reflector-port  {
            type  uint16 {
                 range "1025..65535"  {
                    description "1025..65535:1025-65535";
                 }
            }
            description "";
        } // END of reflector-port definition.

        leaf sender-ip  {
            type  cml-data-types:cml_hostpname_t;
            description "";
        } // END of sender-ip definition.

        leaf dscp  {
            type  string {
                length "1..8";
                pattern "[^?' =,>|]+";
            }
            description "Use this attribute to classify traffic based on the Differentiated
                        Services Code Point (DSCP) value. The DSCP value range is
                        0-63.Warning: In CLI show running, DSCP values with well-known names
                        (ex.: af11, cs0) will be displayed as such.On Netconf, DSCP values
                        will always be numeric. The string type allow up to 8 characters on
                        well-known name.";
        } // END of dscp definition.

    } // END of twamp-session-parameters-config definition.
    grouping uni-link-loss-a-bit-config {
        description
            "Grouping for uni-link-loss a-bit configuration on interface";
        leaf loss-a-bit-min  {
            type  decimal64 {
                 fraction-digits 6;            }
            description "Unidirectional link loss a-bit";
        } // END of loss-a-bit-min definition.

        leaf loss-a-bit-max  {
            type  decimal64 {
                 fraction-digits 6;            }
            description "";
        } // END of loss-a-bit-max definition.

    } // END of uni-link-loss-a-bit-config definition.
    grouping uni-link-delay-a-bit-config {
        description
            "Configuration items for uni-link delay threshold";
        leaf a-bit-min  {
            type  uint32 {
                 range "1..16777215"  {
                    description "1..16777215:Reuse threshold value in microseconds";
                 }
            }
            description "Unidirectional link delay a-bit minimum";
        } // END of a-bit-min definition.

        leaf a-bit-max  {
            type  uint32 {
                 range "1..16777215"  {
                    description "1..16777215:Maximum threshold value in microseconds";
                 }
            }
            units "microseconds";
            description "";
        } // END of a-bit-max definition.

    } // END of uni-link-delay-a-bit-config definition.
    grouping min-max-uni-link-delay-config {
        description
            "Configuration items for min/max delay";
        leaf min-value  {
            type  uint32 {
                 range "1..16777215"  {
                    description "1..16777215:Minimum Unidirectional Link Delay in microseconds";
                 }
            }
            units "microseconds";
            description "Min max Unidirectional link delay";
        } // END of min-value definition.

        leaf max-value  {
            type  uint32 {
                 range "1..16777215"  {
                    description "1..16777215:Maximum Unidirectional Link Delay in microseconds";
                 }
            }
            units "microseconds";
            description "";
        } // END of max-value definition.

    } // END of min-max-uni-link-delay-config definition.
    grouping min-max-uni-link-delay-a-bit-config {
        description
            "Configuration items for min/max delay threshold";
        leaf a-bit-min-range-minimum  {
            type  uint32 {
                 range "1..16777215"  {
                    description "1..16777215:Reuse threshold value of Min-Delay in microseconds";
                 }
            }
            units "microseconds";
            description "Min/Max Unidirectional link delay a-bit";
        } // END of a-bit-min-range-minimum definition.

        leaf a-bit-min-range-maximum  {
            type  uint32 {
                 range "1..16777215"  {
                    description "1..16777215:Reuse threshold value of Max-Delay in microseconds";
                 }
            }
            units "microseconds";
            description "";
        } // END of a-bit-min-range-maximum definition.

        leaf a-bit-max-range-minimum  {
            type  uint32 {
                 range "1..16777215"  {
                    description "1..16777215:Maximum threshold value of Min-Delay in microseconds";
                 }
            }
            units "microseconds";
            description "";
        } // END of a-bit-max-range-minimum definition.

        leaf a-bit-max-range-maximum  {
            type  uint32 {
                 range "1..16777215"  {
                    description "1..16777215:Maximum threshold value of Max-Delay in microseconds";
                 }
            }
            units "microseconds";
            description "";
        } // END of a-bit-max-range-maximum definition.

    } // END of min-max-uni-link-delay-a-bit-config definition.
    grouping igp-te-params-config {
        description
            "Grouping for IGP TE Paramaters";
        container uni-link {
            description
                "Set IGP TE uni-link parameters";
            container config {
                description
                    "Configuration data for IGP-TE parameters";
                uses igp-te-config;
            } // END of config-container definition.
            container state {
                config false;
                description
                    "Operational state data";
                uses igp-te-config;
            } // END of state-container definition.
            container twamp-loss-parameter {
                if-feature feature-list:HAVE_TWAMP;
                description
                    "TWAMP loss parameter";
                container config {
                    description
                        "Configuration data";
                    uses loss-dynamic-config;
                } // END of config-container definition.
                container state {
                    config false;
                    description
                        "Operational state data";
                    uses loss-dynamic-config;
                } // END of state-container definition.
            } // END of twamp-loss-parameter-container definition.
            container twamp-session-parameters {
                if-feature feature-list:HAVE_TWAMP;
                description
                    "TWAMP session parameters";

                list twamp-session-parameter {
                    key "delay-dynamic-twamp reflector-ip";
                    max-elements 1;
                    description
                        "TWAMP session parameter list";
                    leaf delay-dynamic-twamp  {
                        type  leafref {
                            path  "../config/delay-dynamic-twamp";
                        }
                        description "Use this command to start the delay measurement for the interface";
                    } // END of delay-dynamic-twamp definition.

                    leaf reflector-ip  {
                        type  leafref {
                            path  "../config/reflector-ip";
                        }
                        description "";
                    } // END of reflector-ip definition.

                    container config {
                        description
                            "Configuration data";
                        uses twamp-session-parameters-config;
                    } // END of config-container definition.
                    container state {
                        config false;
                        description
                            "Operational state data";
                        uses twamp-session-parameters-config;
                    } // END of state-container definition.
                } // End of twamp-session-parameter-list
            } // END of twamp-session-parameters-container definition.
            container delay-threshold {
                description
                    "This container defines the min and max values for uni-link-delay";

                list a-bit {
                    key "a-bit-min a-bit-max";
                    max-elements 1;
                    description
                        "This objectlist defines the min and max threshold values";
                    leaf a-bit-min  {
                        type  leafref {
                            path  "../config/a-bit-min";
                        }
                        description "Unidirectional link delay a-bit minimum";
                    } // END of a-bit-min definition.

                    leaf a-bit-max  {
                        type  leafref {
                            path  "../config/a-bit-max";
                        }
                        description "";
                    } // END of a-bit-max definition.

                    container config {
                        description
                            "This container defines uni-link-delay threshold configurations.";
                        uses uni-link-delay-a-bit-config;
                    } // END of config-container definition.
                    container state {
                        config false;
                        description
                            "This container defines uni-link-delay threshold Operational
                                    parameters.";
                        uses uni-link-delay-a-bit-config;
                    } // END of state-container definition.
                } // End of a-bit-list
            } // END of delay-threshold-container definition.
            container min-max-delay {
                description
                    "This container defines the min and max values of delay";

                list delay {
                    key "min-value max-value";
                    max-elements 1;
                    description
                        "This objectlist defines the min and max values";
                    leaf min-value  {
                        type  leafref {
                            path  "../config/min-value";
                        }
                        description "Min max Unidirectional link delay";
                    } // END of min-value definition.

                    leaf max-value  {
                        type  leafref {
                            path  "../config/max-value";
                        }
                        description "";
                    } // END of max-value definition.

                    container config {
                        description
                            "This container defines the min/max static configurations.";
                        uses min-max-uni-link-delay-config;
                    } // END of config-container definition.
                    container state {
                        config false;
                        description
                            "This container defines the min/max static Operational parameters.";
                        uses min-max-uni-link-delay-config;
                    } // END of state-container definition.
                } // End of delay-list
            } // END of min-max-delay-container definition.
            container loss {
                description
                    "This container defines the min and max values for uni-link-loss";

                list threshold {
                    key "loss-a-bit-min loss-a-bit-max";
                    max-elements 1;
                    description
                        "This objectlist defines the min and max values for uni-link-loss";
                    leaf loss-a-bit-min  {
                        type  leafref {
                            path  "../config/loss-a-bit-min";
                        }
                        description "Unidirectional link loss a-bit";
                    } // END of loss-a-bit-min definition.

                    leaf loss-a-bit-max  {
                        type  leafref {
                            path  "../config/loss-a-bit-max";
                        }
                        description "";
                    } // END of loss-a-bit-max definition.

                    container config {
                        description
                            "This container defines the min/max static configurations.";
                        uses uni-link-loss-a-bit-config;
                    } // END of config-container definition.
                    container state {
                        config false;
                        description
                            "This container defines the min/max static Operational parameters.";
                        uses uni-link-loss-a-bit-config;
                    } // END of state-container definition.
                } // End of threshold-list
            } // END of loss-container definition.
            container min-max-delay-threshold {
                description
                    "This container defines  the min and max values for
                            min-max-uni-link-delay";

                list a-bit {
                    key "a-bit-min-range-minimum a-bit-min-range-maximum a-bit-max-range-minimum a-bit-max-range-maximum";
                    max-elements 1;
                    description
                        "This objectlist defines the min and max threshold values";
                    leaf a-bit-min-range-minimum  {
                        type  leafref {
                            path  "../config/a-bit-min-range-minimum";
                        }
                        description "Min/Max Unidirectional link delay a-bit";
                    } // END of a-bit-min-range-minimum definition.

                    leaf a-bit-min-range-maximum  {
                        type  leafref {
                            path  "../config/a-bit-min-range-maximum";
                        }
                        description "";
                    } // END of a-bit-min-range-maximum definition.

                    leaf a-bit-max-range-minimum  {
                        type  leafref {
                            path  "../config/a-bit-max-range-minimum";
                        }
                        description "";
                    } // END of a-bit-max-range-minimum definition.

                    leaf a-bit-max-range-maximum  {
                        type  leafref {
                            path  "../config/a-bit-max-range-maximum";
                        }
                        description "";
                    } // END of a-bit-max-range-maximum definition.

                    container config {
                        description
                            "This container defines the min/max static configurations.";
                        uses min-max-uni-link-delay-a-bit-config;
                    } // END of config-container definition.
                    container state {
                        config false;
                        description
                            "This container defines the min/max static Operational parameters.";
                        uses min-max-uni-link-delay-a-bit-config;
                    } // END of state-container definition.
                } // End of a-bit-list
            } // END of min-max-delay-threshold-container definition.
        } // END of uni-link-container definition.
    } // END of igp-te-params-config definition.

    grouping  igp-te-grouping {
    description
        "Configuration data for igp-te";
    container igp-te {
        description
            "Configuration data for igp-te";
        container interfaces {
            description
                "Top level container for interfaces, including configuration and state
                        data";

            list interface {
            // when " !ipi-if-aggregate:member-aggregation ";
                key "name";
                description
                    "IGP TE interfaces";
                leaf name  {
                    type  leafref {
                        path  "/ipi-interface:interfaces/ipi-interface:interface/ipi-interface:name";
                    }
                    description "Interface name for which igp-te params are being configured";
                } // END of name definition.

                uses igp-te-params-config;
            } // End of interface-list
        } // END of interfaces-container definition.
    } // END of igp-te-container definition.
    } // END of igp-te-grouping definition.

    uses igp-te-grouping;

    rpc twamp-clear-measurement-intf {
        description "Clear and restart the twamp measurement on an interface";
        input  {
            leaf interface-name  {
                type string {
                    length "1..128";
                }
                mandatory true;
                description "Interface name";
            }
        }
    }

    rpc twamp-clear-measurement-all {
        description "Clear and restart the twamp measurement on all interfaces";
    }

}

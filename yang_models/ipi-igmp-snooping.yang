/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-igmp-snooping.yang
*
*/

module ipi-igmp-snooping {

    yang-version 1.1;

    namespace   "http://www.ipinfusion.com/yang/ocnos/ipi-igmp-snooping";

    prefix "ipi-igmp-snooping";

    import ipi-igmp-snooping-types {
        prefix ipi-igmp-snooping-types;
        revision-date 2021-11-15;
    }

    import ipi-interface {
        prefix ipi-interface;
        revision-date 2022-04-05;
    }

    import ipi-if-aggregate {
        prefix ipi-if-aggregate;
        revision-date 2022-04-20;
    }

    import ipi-network-instance {
        prefix ipi-network-instance;
        revision-date 2021-11-10;
    }

    import ipi-bridge {
        prefix ipi-bridge;
        revision-date 2022-01-13;
    }

    import ietf-inet-types {
        prefix inet;
        revision-date 2013-07-15;
    }

    import cml-data-types {
        prefix cml-data-types;
        revision-date 2022-04-04;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for IGMP Snooping object";


    revision "2021-11-15" {
        description "Restructured module as per OpenConfig style";
        reference " 0.2.0.";
    }

    revision "2018-06-21" {
        description "Initial Version";
        reference " 0.1.0.";
    }

    grouping igmp-snooping-global-config {
        description
            "Global configuration data for IGMP Snooping";
        leaf disable-igmp-snooping  {
            type  empty;
            description "Use this attribute to disable IGMP Snooping. When this attribute is
                        given in the Configure mode, IGMP snooping is enabled at switch level
                        on all the vlans in switch. When this attribute is given at the VLAN
                        interface level, IGMP Snooping is enabled for that VLAN.";
        } // END of disable-igmp-snooping definition.

        leaf disable-report-suppression  {
            type  empty;
            description "Use this attribute to disable report suppression for IGMP version 1, 2
                        and 3 reports. By default report suppression is enabled.";
        } // END of disable-report-suppression definition.

        leaf unknown-multicast-action  {
            type  ipi-igmp-snooping-types:igmp_snoop_unknown_mcast_action_t;
            default "flood";
            description "Use this attribute to set the action to be taken on receiving l2
                        unknown multicast packets.";
        } // END of unknown-multicast-action definition.

    } // END of igmp-snooping-global-config definition.
    grouping igmp-snooping-debug-config {
        description
            "Debug configuration data for IGMP Snooping";
        leaf debug-options  {
            type  ipi-igmp-snooping-types:igmp_snoop_debug_options_t;
            description "Enable IGMP snooping debug";
        } // END of debug-options definition.

    } // END of igmp-snooping-debug-config definition.
    grouping igmp-snooping-terminal-debug-state {
        description
            "Debug state data for IGMP Snooping";
        leaf terminal-debug-status  {
            type  ipi-igmp-snooping-types:igmp_snoop_debug_options_t;
            description "Terminal debug status";
        } // END of terminal-debug-status definition.

    } // END of igmp-snooping-terminal-debug-state definition.
    grouping igmp-snooping-interface-config {
        description
            "Global configuration data for IGMP Snooping";
        leaf name  {
            type  leafref {
                path  "/ipi-interface:interfaces/ipi-interface:interface/ipi-interface:name";
            }
            description "Interface name";
        } // END of name definition.

        leaf igmp-snooping  {
            type  cml-data-types:cml_enable_disable_t;
            description "Use this attribute to enable or disable IGMP Snooping.When this
                        command is given at the VLAN interface level, IGMP Snooping is enabled
                        for that VLAN.";
        } // END of igmp-snooping definition.

        leaf enable-fast-leave  {
            type  empty;
            description "Use this attribute to enable IGMP Snooping fast-leave processing.
                        Fast-leave processing is analogous to immediateleave processing the
                        IGMP group-membership is removed, as soon as an IGMP leave group
                        message is received without sending out a group-specific query";
        } // END of enable-fast-leave definition.

        leaf report-suppression  {
            type  cml-data-types:cml_enable_disable_t;
            description "Use this attribute to enable or disable report suppression for IGMP
                        version 1, 2 and 3 reports. By default report suppression is enabled.";
        } // END of report-suppression definition.

        leaf mrouter-interface-name  {
            type  leafref {
                path  "/ipi-interface:interfaces/ipi-interface:interface/ipi-interface:name";
            }
            description "Use this attribute to statically configure the specified VLAN
                        constituent interface as a multicast router interface for IGMP
                        Snooping in that VLAN.";
        } // END of mrouter-interface-name definition.

        leaf enable-querier  {
            type  empty;
            description "Use this attribute to enable IGMP snooping querier functionality on a
                        VLAN when IGMP is not enabled on the particular VLAN. When enabled,
                        the IGMP Snooping querier sends out periodic IGMP queries for all
                        interfaces on that VLAN.The IGMP Snooping querier uses the 0.0.0.0
                        source IP address, because it only masquerades as a proxy IGMP querier
                        for faster network convergence. It does not start, or automatically
                        cease, the IGMP Querier operation if it detects query message(s) from
                        a multicast router. It restarts as the IGMP Snooping querier if no
                        queries are seen  within the other querier interval.";
        } // END of enable-querier definition.

    } // END of igmp-snooping-interface-config definition.
    grouping igmp-snooping-static-group-config {
        description
            "Static group configuration data for IGMP Snooping";
        leaf group-address  {
            type  inet:ipv4-address;
            description "Use this attribute to set the static group-address to be joined";
        } // END of group-address definition.

        leaf interface-name  {
            type  string {
                length "1..1965";
                pattern "[^?' =,>|]+";
            }
            description "Use this attribute to statically configure group membership entries on
                        an interface. To statically add only a group membership, do not
                        specify any parameters. This attribute applies to IGMP operation on a
                        specific interface to statically add group and/or source records; on a
                        VLAN interface to statically add group and/or source records.";
        } // END of interface-name definition.

    } // END of igmp-snooping-static-group-config definition.
    grouping igmp-snooping-static-group-source-config {
        description
            "Static group configuration data for IGMP Snooping";
        leaf source-address  {
            type  inet:ipv4-address;
            description "Use this attribute to set the Source Address to be joined";
        } // END of source-address definition.

    } // END of igmp-snooping-static-group-source-config definition.
    grouping igmp-snooping-static-groups-top {
        description
            "Top level container for IGMP snooping static group variables";
        container static-groups {
            description
                "IGMP Snooping static group configurations";
            container ssm-groups {
                description
                    "IGMP Snooping SSM (Source Specific Multicast) Groups";

                list ssm-group {
                    key "group-address source-address interface-name";
                    description
                        "IGMP Snooping SSM group entry";
                    leaf group-address  {
                        type  leafref {
                            path  "../config/group-address";
                        }
                        description "Use this attribute to set the static group-address to be joined";
                    } // END of group-address definition.

                    leaf source-address  {
                        type  leafref {
                            path  "../config/source-address";
                        }
                        description "Use this attribute to set the Source Address to be joined";
                    } // END of source-address definition.

                    leaf interface-name  {
                        type  leafref {
                            path  "../config/interface-name";
                        }
                        description "Use this attribute to statically configure group membership entries on
                                    an interface. To statically add only a group membership, do not
                                    specify any parameters. This attribute applies to IGMP operation on a
                                    specific interface to statically add group and/or source records; on a
                                    VLAN interface to statically add group and/or source records.";
                    } // END of interface-name definition.

                    container config {
                        description
                            "IGMP Snooping global configuration attributes";
                        uses igmp-snooping-static-group-config;
                        uses igmp-snooping-static-group-source-config;
                    } // END of config-container definition.
                    container state {
                        config false;
                        description
                            "IGMP Snooping global state information";
                        uses igmp-snooping-static-group-config;
                        uses igmp-snooping-static-group-source-config;
                    } // END of state-container definition.
                } // End of ssm-group-list
            } // END of ssm-groups-container definition.
            container asm-groups {
                description
                    "IGMP Snooping ASM (Any Source Multicast) Groups";

                list asm-group {
                    key "group-address interface-name";
                    description
                        "IGMP Snooping SSM group entry";
                    leaf group-address  {
                        type  leafref {
                            path  "../config/group-address";
                        }
                        description "Use this attribute to set the static group-address to be joined";
                    } // END of group-address definition.

                    leaf interface-name  {
                        type  leafref {
                            path  "../config/interface-name";
                        }
                        description "Use this attribute to statically configure group membership entries on
                                    an interface. To statically add only a group membership, do not
                                    specify any parameters. This attribute applies to IGMP operation on a
                                    specific interface to statically add group and/or source records; on a
                                    VLAN interface to statically add group and/or source records.";
                    } // END of interface-name definition.

                    container config {
                        description
                            "IGMP Snooping global configuration attributes";
                        uses igmp-snooping-static-group-config;
                    } // END of config-container definition.
                    container state {
                        config false;
                        description
                            "IGMP Snooping global state information";
                        uses igmp-snooping-static-group-config;
                    } // END of state-container definition.
                } // End of asm-group-list
            } // END of asm-groups-container definition.
        } // END of static-groups-container definition.
    } // END of igmp-snooping-static-groups-top definition.
    grouping igmp-snooping-interfaces-top {
        description
            "Top level container for interface level IGMP snooping variables";
        container interfaces {
            description
                "IGMP Snooping interface related Configurations";

            list interface {
            when " not(/ipi-interface:interfaces/ipi-interface:interface/ipi-if-aggregate:member-aggregation) + /ipi-interface:interfaces/ipi-interface:interface/ipi-interface:config/ipi-interface:enable-switchport != '1' ";
                key "name";
                description
                    "IGMP Snooping interface list";
                leaf name  {
                    type  leafref {
                        path  "../config/name";
                    }
                    description "Reference to the base interface name";
                } // END of name definition.

                container config {
                    description
                        "IGMP Snooping interface related Configurations";
                    uses igmp-snooping-interface-config;
                } // END of config-container definition.
                container state {
                    config false;
                    description
                        "Operational data for Igmp Snooping interface";
                    uses igmp-snooping-interface-config;
                } // END of state-container definition.
                uses igmp-snooping-static-groups-top;
            } // End of interface-list
        } // END of interfaces-container definition.
    } // END of igmp-snooping-interfaces-top definition.
    grouping igmp-snooping-top {
        description
            "IGMP Snooping variables top level container";
        container global {
            description
                "IGMP Snooping global configurations";
            container config {
                description
                    "IGMP Snooping global configuration attributes";
                uses igmp-snooping-global-config;
            } // END of config-container definition.
            container state {
                config false;
                description
                    "IGMP Snooping global state information";
                uses igmp-snooping-global-config;
            } // END of state-container definition.
        } // END of global-container definition.
        container debug {
            description
                "IGMP Snooping debug configurations";
            container config {
                description
                    "IGMP Snooping debug configuration attributes";
                uses igmp-snooping-debug-config;
            } // END of config-container definition.
            container state {
                config false;
                description
                    "IGMP Snooping debug state information";
                uses igmp-snooping-debug-config;
                uses igmp-snooping-terminal-debug-state;
            } // END of state-container definition.
        } // END of debug-container definition.
    } // END of igmp-snooping-top definition.

    grouping  igmp-snooping-grouping {
    description
        "Top level container for IGMP Snooping config and operational state
                data";
    container igmp-snooping {
        when " /ipi-network-instance:network-instances/ipi-network-instance:network-instance/ipi-bridge:bridge/ipi-bridge:config/ipi-bridge:protocol ";
        description
            "Top level container for IGMP Snooping config and operational state
                    data";
        uses igmp-snooping-top;
        uses igmp-snooping-interfaces-top;
    } // END of igmp-snooping-container definition.
    } // END of igmp-snooping-grouping definition.

    uses igmp-snooping-grouping;

    rpc igmp-snooping-clear-group-interface {
        description "Use this RPC to clear IGMP snooping entries based on Group and
                    Interface";
        input  {
            leaf group-address  {
                type inet:ipv4-address;
                mandatory true;
                description "Use this attribute to set the group-address on which IGMP entries to
                            be cleared";
            }
            leaf interface-name  {
                type string;
                mandatory true;
                description "Use this attribute to set the interface-name on which IGMP entries to
                            be cleared";
            }
        }
    }

    rpc igmp-snooping-clear-interface {
        description "Use this RPC to clear IGMP snooping entries based on interface";
        input  {
            leaf interface-name  {
                type string;
                mandatory true;
                description "Use this attribute to set the interface-name on which IGMP entries to
                            be cleared";
            }
        }
    }

    rpc igmp-snooping-clear-all {
        description "Use this RPC to clear all IGMP snooping entries";
    }

    rpc igmp-snooping-clear-group {
        description "Use this RPC to clear IGMP snooping based on Group";
        input  {
            leaf group-address  {
                type inet:ipv4-address;
                mandatory true;
                description "Use this attribute to set the group-address on which cache entries to
                            be cleared";
            }
        }
    }

    rpc igmp-snooping-terminal-debugging-on {
        description "Use this RPC to enable IGMP snooping debugging";
        input  {
            leaf debug-options  {
                type ipi-igmp-snooping-types:igmp_snoop_debug_options_t;
                mandatory true;
                description "Debug-option to be enabled";
            }
        }
    }

    rpc igmp-snooping-terminal-debugging-off {
        description "Use this RPC to disable IGMP snooping debugging";
        input  {
            leaf debug-options  {
                type ipi-igmp-snooping-types:igmp_snoop_debug_options_t;
                mandatory true;
                description "Debug-option to be disabled";
            }
        }
    }

}

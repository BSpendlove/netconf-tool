/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-cross-connect-types.yang
*
*/

module ipi-cross-connect-types {

    yang-version 1.1;

    namespace   "http://www.ipinfusion.com/yang/ocnos/ipi-cross-connect-types";

    prefix "ipi-cross-connect-types";

    organization
        "IP Infusion Inc.";

    contact
        "Address: 3965 Freedom Circle, Suite 200, Santa Clara, CA 95054
         Phone: +1 408-400-1900
         E-mail: support@ipinfusion.com
         Web: http://www.ipinfusion.com/";

    description
        "Cross-Connect Types";


    revision "2021-11-10" {
        description "Initial Version";
        reference " 0.1.0.";
    }



    typedef  xc_oper_status_t {
        type enumeration {
            enum Down {
                value 0;
                description "Cross Connect Down";
            }
            enum Up {
                value 1;
                description "Cross Connect Up";
            }
        }
        description "type definition for XC_OPER_STATUS_T";
    }

}

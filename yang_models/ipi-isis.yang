/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-isis.yang
*
*/

module ipi-isis {

    yang-version 1.1;

    namespace   "http://www.ipinfusion.com/yang/ocnos/ipi-isis";

    prefix "ipi-isis";

    import ipi-vrf {
        prefix ipi-vrf;
        revision-date 2021-09-03;
    }

    import ipi-network-instance {
        prefix ipi-network-instance;
        revision-date 2021-11-10;
    }

    import ipi-isis-types {
        prefix ipi-isis-types;
        revision-date 2022-02-07;
    }

    import ietf-inet-types {
        prefix inet;
        revision-date 2013-07-15;
    }

    import ipi-interface {
        prefix ipi-interface;
        revision-date 2022-04-05;
    }

    import feature-list {
        prefix feature-list;
        revision-date 2022-07-13;
    }

    include ipi-isis-extended { revision-date 2021-09-03;}
    include ipi-isis-lsp { revision-date 2021-09-03;}
    include ipi-isis-interface { revision-date 2022-04-04;}
    include ipi-isis-sr { revision-date 2021-09-03;}
    include ipi-isis-cspf { revision-date 2021-09-03;}
    organization
        "IP Infusion Inc.";

    contact
        "Address: 3965 Freedom Circle, Suite 200, Santa Clara, CA 95054
         Phone: +1 408-400-1900
         E-mail: support@ipinfusion.com
         Web: http://www.ipinfusion.com/";

    description
        "Model for managing IS-IS Instance";


    revision "2022-04-04" {
        description "Added if-feature whereever needed";
        reference " 0.7.0.";
    }

    revision "2022-02-07" {
        description "Datamodel change for isis ol-bit on-startup and net commands";
        reference " 0.6.0.";
    }

    revision "2021-12-07" {
        description "Datamodel change for debug isis cspf command";
        reference " 0.5.1.";
    }

    revision "2021-09-08" {
        description "Datamodel change for passive-interface command";
        reference " 0.5.0.";
    }

    revision "2021-09-03" {
        description "Update descriptions of attribute";
        reference " 0.5.0.";
    }

    revision "2021-08-16" {
        description "ISIS-TE Metric Extension's GET API support";
        reference " 0.4.0.";
    }

    revision "2021-01-11" {
        description " 1.JIRA-42469:changed redistribute-level-1-2 and redistribute-level-2-1 as objectlist with
                        enable as RDN
                        2.JIRA-42382:redistribute config is not retained after system upgrade from SP3.0.135 build to SP4.1.188 Nebula branch
        ";
        reference " 0.3.0.";
    }

    revision "2020-12-15" {
        description "Change to have data-types in lower case instead of camel case";
        reference " 0.2.0.";
    }

    revision "2020-05-06" {
        description "Datamodel restructuring";
        reference " 0.1.0.";
    }

    grouping isis-notif-state {
        description
            "State items for ISIS notification";
        leaf lsp-identifier  {
            type  leafref {
                path  "/ipi-isis:isis/ipi-isis:isis-instance/ipi-isis:level-runtime/ipi-isis:lspdb/ipi-isis:state/ipi-isis:lsp-identifier";
            }
            config false;
            description "LSP ID";
        } // END of lsp-identifier definition.

        leaf overload  {
            type  leafref {
                path  "/isis/isis-instance/state/overload";
            }
            config false;
            description "New overload state of the IS-IS instance";
        } // END of overload definition.

        leaf pdu-length  {
            type  leafref {
                path  "/ipi-isis:isis/ipi-isis:isis-instance/ipi-isis:level-runtime/ipi-isis:lspdb/ipi-isis:state/ipi-isis:pdu-length";
            }
            config false;
            description "Size of the LSP PDU";
        } // END of pdu-length definition.

        leaf raw-pdu  {
            type  string {
                length "1..1965";
            }
            config false;
            description "Received raw PDU";
        } // END of raw-pdu definition.

        leaf pdu-field-len  {
            type  uint8;
            config false;
            description "Size of the ID length in the received PDU";
        } // END of pdu-field-len definition.

        leaf max-area-addresses  {
            type  uint8;
            config false;
            description "Received number of supported areas";
        } // END of max-area-addresses definition.

        leaf protocol-version  {
            type  uint8;
            config false;
            description "Protocol version received in the PDU";
        } // END of protocol-version definition.

        leaf reason  {
            type  string {
                length "1..1965";
                pattern "[^?' =,>|]+";
            }
            config false;
            description "string describing the reason";
        } // END of reason definition.

        leaf protocols  {
            type  uint8;
            config false;
            description "List of protocols supported by the remote system";
        } // END of protocols definition.

        leaf error-offset  {
            type  uint32;
            config false;
            description "If the problem is a malformed TLV, the error-offset points to the
                        start of the TLV. If the problem is with the LSP header, the
                        error-offset points to the errant byte";
        } // END of error-offset definition.

        leaf tlv-type  {
            type  uint8;
            config false;
            description "If the problem is a malformed TLV, the tlv-type is set to the type
                        value of the suspicious TLV. Otherwise, this leaf is not presen";
        } // END of tlv-type definition.

        leaf global-block-base  {
            if-feature feature-list:HAVE_ISIS_SR;
            type  int32;
            config false;
            description "Start ID";
        } // END of global-block-base definition.

        leaf global-block-range  {
            if-feature feature-list:HAVE_ISIS_SR;
            type  int32;
            config false;
            description "End ID";
        } // END of global-block-range definition.

        leaf received-index  {
            if-feature feature-list:HAVE_ISIS_SR;
            type  uint32;
            config false;
            description "Index";
        } // END of received-index definition.

        leaf routing-protocol  {
            if-feature feature-list:HAVE_ISIS_SR;
            type  string {
                length "1..1965";
                pattern "[^?' =,>|]+";
            }
            config false;
            description "Module Name";
        } // END of routing-protocol definition.

    } // END of isis-notif-state definition.
    grouping isis-global-config {
        description
            "Global Configuration items for ISIS";
        leaf instance  {
            type  string {
                length "1..1965";
                pattern "[^?' =,>|]+";
            }
            description "Use this attribute to initiate an ISIS routing instance.Configure at
                        least one NET to start routing.";
        } // END of instance definition.

        leaf distance  {
            type  uint8 {
                 range "1..255"  {
                    description "1..255:range";
                 }
            }
            default "115";
            description "Use this attribute to set the administrative distance for all IPv4
                        routes.";
        } // END of distance definition.

        leaf vrf-name  {
            type  leafref {
                path  "/ipi-network-instance:network-instances/ipi-network-instance:network-instance/ipi-vrf:vrf/ipi-vrf:config/ipi-vrf:vrf-name";
            }
            mandatory true;
            description "VRF Name to associate with this instance";
        } // END of vrf-name definition.

        leaf dynamic-host-name  {
            type  ipi-isis-types:isis_dynamic_hostanme_t;
            default "dynamic-hostname";
            description "Use this attribute to configure the hostname to be advertised for an
                        ISIS instance using the dynamic hostname exchange mechanism (RFC 2763)
                        and system-ID-to-hostname translation.This command configures a
                        hostname to be used for the Dynamic Hostname Exchange Mechanism and
                        System-ID tohostname translation. Use the routing area tag as the
                        hostname, not the router.s global hostname";
        } // END of dynamic-host-name definition.

        leaf disable-adjacency-check  {
            type  empty;
            description "Use this attribute to configure the policy of adjacency based on the
                        protocol related TLVs in the ISIS Hello packet. ISIS checks adjacency
                        with protocol related TLVs including Protocols Supported TLV or IP
                        Interface Address TLV by default. The command with no parameter
                        disables this check.";
        } // END of disable-adjacency-check definition.

        leaf ignore-lsp-errors  {
            type  empty;
            description "Use this attribute to ignore LSPs with checksum errors. By default,
                        ISIS validates checksum for LSP whenever it receives LSPs and if the
                        checksum has an error, the LSP will be dropped. Configuring this
                        command to ignore the LSP checksum error and treat it as if checksum
                        is passed.";
        } // END of ignore-lsp-errors definition.

        leaf lfa-hold-timer  {
            if-feature feature-list:HAVE_ISIS_LFA;
            type  int32 {
                 range "100..100000"  {
                    description "100..100000:Set Hold On interval in milliseconds";
                 }
            }
            default "1000";
            description "LFA terminate-hold-on interval";
        } // END of lfa-hold-timer definition.

        leaf protocol-topology  {
            when " /ipi-isis:isis/ipi-isis:isis-instance/ipi-isis:metric/ipi-isis:config/ipi-isis:style ";
            if-feature feature-list:HAVE_PROTOCOL_TOPOLOGY;
            type  empty;
            description "Use this attribute to configure ISIS Protocol Topology Support.";
        } // END of protocol-topology definition.

        leaf level-capability  {
            type  ipi-isis-types:isis_is_type_t;
            default "level-1-2";
            description "Use this attribute to set the IS to the specified level of
                        routing.Changing is-type brings down, then brings up a particular
                        level of routing. There is a limitation: Only one ISIS instance can
                        run Level-2 routing (either Level-2 only IS, or Level-1-2 IS)";
        } // END of level-capability definition.

        leaf authentication-send-only  {
            type  ipi-isis-types:isis_auth_level_type_t;
            default "level-1-2";
            description "Use this attribute to set the send-only option at the instance
                        level.Use this command before configuring the authentication mode and
                        authentication key-chain, so that the implementation of authentication
                        goes smoothly. That is, the routers will have more time for the keys
                        to be configured on each router if authentication is inserted only on
                        the packets being sent, not checked on packets being received. After
                        all routers that must communicate are configured with this command,
                        enable the authentication mode and key chain on each router.";
        } // END of authentication-send-only definition.

        leaf incremental-spf-levels  {
            type  ipi-isis-types:isis_is_type_t;
            default "level-1-2";
            description "Use this attribute to enable incremental SPF for a routing process";
        } // END of incremental-spf-levels definition.

        leaf priority-tag  {
            if-feature feature-list:HAVE_WIDE_METRIC;
            type  uint32 {
                 range "1..4294967295"  {
                    description "1..4294967295:Tag value";
                 }
            }
            description "Use this attribute to set a high priority tag value";
        } // END of priority-tag definition.

        leaf enable-cspf-capability  {
            when " /ipi-isis:isis/ipi-isis:isis-instance/ipi-isis:config/ipi-isis:enable-mpls-traffic-engg-level-1  or /ipi-isis:isis/ipi-isis:isis-instance/ipi-isis:config/ipi-isis:enable-mpls-traffic-engg-level-2 ";
            if-feature feature-list:HAVE_ISIS_CSPF;
            type  empty;
            description "Use this attribute to enable the constrained shortest path first
                        (CSPF) feature in the ISIS module. CSPF calculates            optimum
                        explicit route (ER), using Traffic Engineering Database and (TED) and
                        pre-existing Label Switched Path (LSP). The resulting ER is used by a
                        signaling protocol (RSVP-TE) to set up LSPs.";
        } // END of enable-cspf-capability definition.

        leaf disable-gr-capability  {
            if-feature feature-list:HAVE_RESTART;
            type  empty;
            description "Use this attribute to enable the GR";
        } // END of disable-gr-capability definition.

        leaf enable-bfd-all-interfaces  {
            if-feature feature-list:HAVE_BFD;
            type  empty;
            description "Use this attribute to enable the Bidirectional Forwarding Detection
                        (BFD) feature on the interfaces enabled with this              ISIS
                        instance. This command sets BFD fall-over check for all the neighbors
                        under specified process.";
        } // END of enable-bfd-all-interfaces definition.

        leaf maximum-area-addresses  {
            type  uint8 {
                 range "3..254"  {
                    description "3..254:Maximum area address that can be supported";
                 }
            }
            default "3";
            description "Use this attribute to set the maximum number of ISIS areas that can be
                        configured on this router with the net command. By default, ISIS
                        permits a maximum of three areas that can be defined on a router.";
        } // END of maximum-area-addresses definition.

        leaf distribute-bgp-ls  {
            if-feature feature-list:HAVE_BGP_LS;
            type  ipi-isis-types:isis_bgp_ls_type_t;
            description "Use this attribute to distribute linkstate and TE Database to BGP";
        } // END of distribute-bgp-ls definition.

    } // END of isis-global-config definition.
    grouping isis-net-config {
        description
            "Configure NET for ISIS instance";
        leaf-list net  {
            type  string {
                length "1..1965";
                pattern "[^?' =,>|]+";
            }
            description "Use this attribute to add a Network Entity Title (NET) for the
                        instance.On a router running ISIS, a NET can be 8 to 20 bytes in
                        length. The last byte is always the n-selector, and must be zero. The
                        n-selector indicates no transport entity, and means that the packet is
                        for the routing software of the system. The six bytes directly
                        preceding the n-selector are the system ID. The system ID length is a
                        fixed size and cannot be changed. The system ID must be unique
                        throughout each area (Level 1) and throughout the backbone (Level 2).
                        The bytes preceding the system ID are the area ID, which can be from 1
                        - 13 bytes in length. By default, a maximum of three NETs per router
                        are allowed with a different area ID but the system ID should be the
                        same for all NETs. You can increase the number of area IDs per system
                        ID with the max-area-address command.";
        } // END of net definition.

    } // END of isis-net-config definition.
    grouping isis-mpls-traffic-engg-config {
        description
            "Configuration items for ISIS MPLS Traffic Engineering";
        leaf enable-mpls-traffic-engg-level-1  {
            when " /ipi-isis:isis/ipi-isis:isis-instance/ipi-isis:metric/ipi-isis:config/ipi-isis:style + /ipi-isis:isis/ipi-isis:isis-instance/ipi-isis:metric/ipi-isis:config/ipi-isis:style = 'wide' + /ipi-isis:isis/ipi-isis:isis-instance/ipi-isis:metric/ipi-isis:config/ipi-isis:level-number != 'level-2' + /ipi-isis:isis/ipi-isis:isis-instance/ipi-isis:config/ipi-isis:level-capability != 'level-2-only' ";
            if-feature feature-list:HAVE_ISIS_TE;
            type  empty;
            description "Use this attribute to configure MPLS Traffic Engineering feature for
                        ISIS.";
        } // END of enable-mpls-traffic-engg-level-1 definition.

        leaf enable-mpls-traffic-engg-level-2  {
            when " /ipi-isis:isis/ipi-isis:isis-instance/ipi-isis:metric/ipi-isis:config/ipi-isis:style + /ipi-isis:isis/ipi-isis:isis-instance/ipi-isis:metric/ipi-isis:config/ipi-isis:style = 'wide' + /ipi-isis:isis/ipi-isis:isis-instance/ipi-isis:metric/ipi-isis:config/ipi-isis:level-number != 'level-1' + /ipi-isis:isis/ipi-isis:isis-instance/ipi-isis:config/ipi-isis:level-capability != 'level-1' ";
            if-feature feature-list:HAVE_ISIS_TE;
            type  empty;
            description "Use this attribute to configure MPLS Traffic Engineering feature for
                        ISIS.";
        } // END of enable-mpls-traffic-engg-level-2 definition.

    } // END of isis-mpls-traffic-engg-config definition.
    grouping isis-global-state {
        description
            "Global State items for ISIS";
        leaf next-global-update-level-1  {
            type  uint32;
            description "Time remaining for next global update";
        } // END of next-global-update-level-1 definition.

        leaf next-global-update-level-2  {
            type  uint32;
            description "Time remaining for next global update";
        } // END of next-global-update-level-2 definition.

        leaf overload  {
            type  ipi-isis-types:isis_overload_state_t;
            description "New overload state of the IS-IS instance";
        } // END of overload definition.

    } // END of isis-global-state definition.
    grouping isis-adjacency-counter-state {
        description
            "State items for ISIS Adjacency Counters";
        leaf system-level-1-adjacency-count  {
            type  uint32;
            description "System level 1 adjacency count";
        } // END of system-level-1-adjacency-count definition.

        leaf system-level-2-adjacency-count  {
            type  uint32;
            description "System level 2 adjacency count";
        } // END of system-level-2-adjacency-count definition.

        leaf system-total-adjacency-count  {
            type  uint32;
            description "System total adjacency count";
        } // END of system-total-adjacency-count definition.

    } // END of isis-adjacency-counter-state definition.
    grouping isis-igp-shortcut-lsp-state {
        description
            "State items for ISIS IGP Shortcut";
        leaf index  {
            type  uint32;
            description "Index";
        } // END of index definition.

        leaf metric  {
            type  uint16;
            description "Metric Value";
        } // END of metric definition.

        leaf tunnel-id  {
            type  uint32;
            description "Tunnel ID";
        } // END of tunnel-id definition.

        leaf tunnel-endpoint  {
            type  string {
                length "1..1965";
                pattern "[^?' =,>|]+";
            }
            description "Tunnel Endpoint";
        } // END of tunnel-endpoint definition.

        leaf lock  {
            type  uint16;
            description "Lock";
        } // END of lock definition.

        leaf status  {
            type  ipi-isis-types:isis_igp_shortcut_lsp_status_t;
            description "Status";
        } // END of status definition.

    } // END of isis-igp-shortcut-lsp-state definition.
    grouping isis-prc-config {
        description
            "Configuration items for ISIS PRC";
        leaf minimum-delay  {
            type  uint32 {
                 range "0..2147483647"  {
                    description "0..2147483647:Minimum Delay between receiving a change to SPF
                            calculation in milliseconds";
                 }
            }
            description "Minimum delay between receiving a change to PRC calculation in
                        milliseconds.Default value is 500";
        } // END of minimum-delay definition.

        leaf maximum-delay  {
            type  uint32 {
                 range "0..2147483647"  {
                    description "0..2147483647:Maximum Delay between receiving a change to SPF
                            calculation in milliseconds";
                 }
            }
            description "Maximum delay between receiving a change to PRC calculation in
                        milliseconds.Default value is 50000";
        } // END of maximum-delay definition.

    } // END of isis-prc-config definition.
    grouping isis-area-auth-config {
        description
            "Configuration items for ISIS Area Authentication";
        leaf area-password  {
            type  string {
                length "1..1965";
                pattern "[^?' =,>|]+";
            }
            mandatory true;
            description "Use this attribute to set the authentication password for the Level-1
                        area and to set authentication on Level-1 SNP PDUs. This command
                        enables authentication when receiving and sending LSP and SNP PDU in
                        Level-1 areas. Area password must be the same for all the ISIS routers
                        in the same area";
        } // END of area-password definition.

        leaf sequence-number-packet  {
            when " /ipi-isis:isis/ipi-isis:isis-instance/ipi-isis:area-authentication/ipi-isis:config/ipi-isis:area-password ";
            type  ipi-isis-types:isis_snp_t;
            description "Use this attribute to set the authentication password for the Level-1
                        area and to set authentication on Level-1 SNP PDUs. This command
                        enables authentication when receiving and sending LSP and SNP PDU in
                        Level-1 areas. Area password must be the same for all the ISIS routers
                        in the same area";
        } // END of sequence-number-packet definition.

    } // END of isis-area-auth-config definition.
    grouping isis-domain-auth-config {
        description
            "Configuration items for ISIS Domain Authentication";
        leaf domain-password  {
            type  string {
                length "1..1965";
                pattern "[^?' =,>|]+";
            }
            mandatory true;
            description "Use this attribute to set the authentication password for the Level-2
                        domain, and optionally, the authentication password on Level-2 SNP
                        PDUs.Configuring this command to enable authentication when receiving
                        and sending LSP and SNP PDU in Level-2 domain. Domain password must be
                        the same in Level-2 domain.";
        } // END of domain-password definition.

        leaf domain-snp  {
            when " /ipi-isis:isis/ipi-isis:isis-instance/ipi-isis:domain-authentication/ipi-isis:config/ipi-isis:domain-password ";
            type  ipi-isis-types:isis_snp_t;
            description "Use this attribute to set the authentication password for the Level-2
                        domain, and optionally, the authentication password on Level-2 SNP
                        PDUs.Configuring this command to enable authentication when receiving
                        and sending LSP and SNP PDU in Level-2 domain. Domain password must be
                        the same in Level-2 domain.";
        } // END of domain-snp definition.

    } // END of isis-domain-auth-config definition.
    grouping isis-passive-interface-top {
        description
            "Grouping for ISIS passive interface";
        container passive-interfaces {
            description
                "ISIS passive interfaces";
            container config {
                description
                    "Configuration data for ISIS passive interface all";
                uses isis-passive-interface-all-config;
            } // END of config-container definition.
            container state {
                config false;
                description
                    "Operational state data for ISIS passive interface all";
                uses isis-passive-interface-all-config;
            } // END of state-container definition.
            uses isis-passive-interface-name-top;
            uses isis-disable-passive-interface-name-top;
        } // END of passive-interfaces-container definition.
    } // END of isis-passive-interface-top definition.
    grouping isis-passive-interface-name-top {
        description
            "Grouping for isis passive interface name";

        list passive-interface {
            key "name";
            description
                "List of ISIS passive interfaces";
            leaf name  {
                type  leafref {
                    path  "../config/name";
                }
                description "Use this attribute to set interface as passive.";
            } // END of name definition.

            container config {
                description
                    "Configuration data for ISIS passive interface";
                uses isis-passive-interface-name-config;
            } // END of config-container definition.
            container state {
                config false;
                description
                    "Operational state data for ISIS passive interface state";
                uses isis-passive-interface-name-config;
            } // END of state-container definition.
        } // End of passive-interface-list
    } // END of isis-passive-interface-name-top definition.
    grouping isis-passive-interface-name-config {
        description
            "Grouping for ISIS passive interface configuration data";
        leaf name  {
            type  leafref {
                path  "/ipi-interface:interfaces/ipi-interface:interface/ipi-interface:name";
            }
            description "Use this attribute to set interface as passive.";
        } // END of name definition.

    } // END of isis-passive-interface-name-config definition.
    grouping isis-disable-passive-interface-name-top {
        description
            "Grouping for disabled isis passive interface name";

        list disable-passive-interface {
            key "name";
            description
                "List of ISIS passive interfaces disabled";
            leaf name  {
                type  leafref {
                    path  "../config/name";
                }
                description "Use this attribute to set interface as passive.";
            } // END of name definition.

            container config {
                description
                    "Configuration data for ISIS passive interface disable";
                uses isis-disable-passive-interface-name-config;
            } // END of config-container definition.
            container state {
                config false;
                description
                    "Operational state data for ISIS passive interface disable state";
                uses isis-disable-passive-interface-name-config;
            } // END of state-container definition.
        } // End of disable-passive-interface-list
    } // END of isis-disable-passive-interface-name-top definition.
    grouping isis-disable-passive-interface-name-config {
        description
            "Grouping for ISIS disable passive interface configuration data";
        leaf name  {
            type  leafref {
                path  "/ipi-interface:interfaces/ipi-interface:interface/ipi-interface:name";
            }
            description "Use this attribute to disbale passive interface.";
        } // END of name definition.

    } // END of isis-disable-passive-interface-name-config definition.
    grouping isis-metric-config {
        description
            "Configuration items for ISIS Metric";
        leaf style  {
            if-feature feature-list:HAVE_WIDE_METRIC;
            type  ipi-isis-types:isis_metric_style_t;
            description "Use this attribute to configure the ISIS metric style";
        } // END of style definition.

        leaf level-number  {
            if-feature feature-list:HAVE_WIDE_METRIC;
            type  ipi-isis-types:isis_level3_t;
            description "Use this attribute to configure the ISIS metric style";
        } // END of level-number definition.

    } // END of isis-metric-config definition.
    grouping isis-area-addr-state {
        description
            "State items for ISIS Metric";
        leaf-list address  {
            type  string {
                length "1..1965";
                pattern "[^?' =,>|]+";
            }
            description "Manual Area Addresses";
        } // END of address definition.

    } // END of isis-area-addr-state definition.
    grouping isis-recv-area-addr-state {
        description
            "State items for ISIS Recv Area Address";
        leaf-list address  {
            type  string {
                length "1..1965";
                pattern "[^?' =,>|]+";
            }
            description "Rcv Area Addresses - other than already in Manual area addr list";
        } // END of address definition.

    } // END of isis-recv-area-addr-state definition.
    grouping isis-lsp-timers-config {
        description
            "Configuration items for ISIS LSP Timers";
        leaf lsp-refresh-interval  {
            type  uint16 {
                 range "1..65535"  {
                    description "1..65535:LSP refresh time in seconds";
                 }
            }
            default "900";
            description "Use this attribute to set the LSP refresh interval.IP Infusion Inc.
                        recommends making the lsp-refresh-interval smaller than
                        max-lsp-lifetime value.";
        } // END of lsp-refresh-interval definition.

        leaf lsp-lifetime-interval  {
            type  uint16 {
                 range "350..65535"  {
                    description "350..65535:Maximum LSP lifetime in seconds";
                 }
            }
            default "1200";
            description "Use this attribute to set the maximum LSP lifetime. You must set
                        max-lsp-lifetime greater than lsp-refreshinterval.";
        } // END of lsp-lifetime-interval definition.

    } // END of isis-lsp-timers-config definition.
    grouping isis-te-ipv4-router-id-config {
        description
            "Configuration items for ISIS IPv4 router id";
        leaf ipv4-router-id  {
            if-feature feature-list:HAVE_ISIS_TE;
            type  inet:ipv4-address;
            description "Use this attribute to configure the traffic engineering stable IP
                        address for a system.";
        } // END of ipv4-router-id definition.

    } // END of isis-te-ipv4-router-id-config definition.
    grouping isis-te-ipv6-router-id-config {
        description
            "Configuration items for ISIS IPv6 router id";
        leaf ipv6-router-id  {
            if-feature feature-list:HAVE_ISIS_TE;
            if-feature feature-list:HAVE_IPV6;
            type  inet:ipv6-address;
            description "Use this attribute to configure the traffic engineering stable IPv6
                        address for a system.";
        } // END of ipv6-router-id definition.

    } // END of isis-te-ipv6-router-id-config definition.
    grouping isis-passive-interface-all-config {
        description
            "Grouping for ISIS passive interface all configuration data";
        leaf passive-interface-all  {
            type  empty;
            description "Use this attribute to set all interfaces as passive.";
        } // END of passive-interface-all definition.

    } // END of isis-passive-interface-all-config definition.
    grouping isis-route-state {
        description
            "State items for ISIS Route";
        leaf destination-prefix  {
            type  inet:ipv4-prefix;
            description "Destination Prefix";
        } // END of destination-prefix definition.

        leaf destination-path-metric  {
            type  uint32;
            description "Destination Path Metric";
        } // END of destination-path-metric definition.

        leaf destination-path-type  {
            type  string {
                length "1..1965";
                pattern "[^?' =,>|]+";
            }
            description "Destination Path Type";
        } // END of destination-path-type definition.

        leaf is-destination-path-type-external  {
            type  boolean;
            description "Destination Path Type External";
        } // END of is-destination-path-type-external definition.

        leaf tunnel-lsp-metric  {
            if-feature feature-list:HAVE_MPLS;
            type  uint32;
            description "Tunnel LSP Metric";
        } // END of tunnel-lsp-metric definition.

        leaf tunnel-lsp-tunnel-identifier  {
            if-feature feature-list:HAVE_MPLS;
            type  uint32;
            description "Tunnel LSP Tunnel Endpoint";
        } // END of tunnel-lsp-tunnel-identifier definition.

        leaf tunnel-lsp-tunnel-endpoint  {
            if-feature feature-list:HAVE_MPLS;
            type  inet:ipv4-prefix;
            description "Tunnel LSP Tunnel Endpoint";
        } // END of tunnel-lsp-tunnel-endpoint definition.

    } // END of isis-route-state definition.
    grouping isis-route-nh-state {
        description
            "State items for ISIS Next Hop";
        leaf nexthop-ip  {
            type  inet:ipv4-address;
            description "Prefix";
        } // END of nexthop-ip definition.

        leaf outgoing-interface  {
            type  string {
                length "1..1965";
                pattern "[^?' =,>|]+";
            }
            description "Outgoing Port";
        } // END of outgoing-interface definition.

        leaf redistribute-map-tag  {
            type  uint32;
            description "Redist Map Tag";
        } // END of redistribute-map-tag definition.

        leaf source-identifier  {
            type  string {
                length "1..1965";
                pattern "[^?' =,>|]+";
            }
            description "Nexthop neighbor source ID";
        } // END of source-identifier definition.

    } // END of isis-route-nh-state definition.
    grouping isis-ipv6-route-state {
        description
            "State items for ISIS IPv6 Route";
        leaf destination-prefix  {
            type  inet:ipv6-prefix;
            description "Destination Prefix";
        } // END of destination-prefix definition.

        leaf destination-path-metric  {
            type  uint32;
            description "Destination Path Metric";
        } // END of destination-path-metric definition.

        leaf destination-path-type  {
            type  string {
                length "1..1965";
                pattern "[^?' =,>|]+";
            }
            description "Destination Path Type";
        } // END of destination-path-type definition.

        leaf is-destination-path-type-external  {
            type  boolean;
            description "Destination Path Type External";
        } // END of is-destination-path-type-external definition.

    } // END of isis-ipv6-route-state definition.
    grouping isis-ipv6-route-nh-state {
        description
            "State items for ISIS IPv6 Route Next Hop";
        leaf nexthop-ip  {
            type  inet:ipv6-address;
            description "Nexthop Prefix";
        } // END of nexthop-ip definition.

        leaf outgoing-interface  {
            type  string {
                length "1..1965";
                pattern "[^?' =,>|]+";
            }
            description "Outgoing Port";
        } // END of outgoing-interface definition.

        leaf redistribute-map-tag  {
            type  uint32;
            description "Redistribute Map Tag";
        } // END of redistribute-map-tag definition.

    } // END of isis-ipv6-route-nh-state definition.
    grouping isis-af-ipv6-config {
        description
            "Configuration items for ISIS AF IPv6";
        leaf afi-name  {
            type  ipi-isis-types:isis_address_ipv6_t;
            mandatory true;
            description "Use this attribute to configure IPv6 routing specific configuration";
        } // END of afi-name definition.

        leaf administrative-distance  {
            type  uint32 {
                 range "1..255"  {
                    description "1..255:Distance range";
                 }
            }
            default "115";
            description "Use this attribute to set the administrative distance for all IPv6
                        routes";
        } // END of administrative-distance definition.

        leaf disable-adjacency-check  {
            type  empty;
            description "Use this attribute to configure the policy of adjacency based on the
                        protocol related TLVs in the ISIS Hello packet. ISIS checks adjacency
                        with protocol related TLVs including Protocols Supported TLV or IP
                        Interface Address TLV by default. The command with no parameter
                        disables this check.";
        } // END of disable-adjacency-check definition.

    } // END of isis-af-ipv6-config definition.
    grouping isis-af-ipv6-redist-1-2-config {
        description
            "Configuration items for ISIS AF IPv6 Redist level 1 into level 2";
        leaf enable  {
            type  empty;
            description "Use this attribute to redistribute reachability information from one
                        level to the other level. If an distribute-list name is given with
                        this command for an access list that does not exist, the routes are
                        still redistributed.";
        } // END of enable definition.

        leaf level-1-acl  {
            type  string {
                length "1..1965";
                pattern "[^?' =,>|]+";
            }
            description "Use this attribute to redistribute reachability information from one
                        level to the other level. If an distribute-list name is given with
                        this command for an access list that does not exist, the routes are
                        still redistributed.";
        } // END of level-1-acl definition.

    } // END of isis-af-ipv6-redist-1-2-config definition.
    grouping isis-af-ipv6-redist-2-1-config {
        description
            "Configuration items for ISIS AF IPv6 Redist level 2 into level 1";
        leaf enable  {
            type  empty;
            description "Use this attribute to redistribute reachability information from one
                        level to the other level. If an distribute-list name is given with
                        this command for an access list that does not exist, the routes are
                        still redistributed.";
        } // END of enable definition.

        leaf level-2-acl  {
            type  string {
                length "1..1965";
                pattern "[^?' =,>|]+";
            }
            description "Use this attribute to redistribute reachability information from one
                        level to the other level. If an distribute-list name is given with
                        this command for an access list that does not exist, the routes are
                        still redistributed.";
        } // END of level-2-acl definition.

    } // END of isis-af-ipv6-redist-2-1-config definition.
    grouping isis-af-ipv6-default-info-config {
        description
            "Configuration items for ISIS AF Default Info";
        leaf originate  {
            type  ipi-isis-types:isis_origin_type_t;
            description "Use this attribute to set originate reachability information to
                        Default destination into LSP.There is no default information in
                        Level-2 domain by default, while Level-1 router calculates default to
                        L1L2 route during SPF calculation. This command enables to originate
                        default route into Level-2 domain.";
        } // END of originate definition.

        leaf route-map-name  {
            when " /ipi-isis:isis/ipi-isis:isis-instance/ipi-isis:address-family-ipv6/ipi-isis:default-route-information/ipi-isis:config/ipi-isis:originate ";
            type  string {
                length "0..1965";
                pattern "[^?' =,>|]*";
            }
            default "";
            description "Route-map Name";
        } // END of route-map-name definition.

    } // END of isis-af-ipv6-default-info-config definition.
    grouping isis-ipv6-proto-redist-config {
        description
            "Configuration items for ISIS Protocol Redist";
        leaf ipv6-protocol-type  {
            type  ipi-isis-types:isis_redistribute_t;
            description "Use this attribute to redistribute routes from another protocol into
                        the ISIS routing table.";
        } // END of ipv6-protocol-type definition.

    } // END of isis-ipv6-proto-redist-config definition.
    grouping isis-ipv6-redist-config {
        description
            "Configuration items for ISIS Redist";
        leaf ipv6-level  {
            type  ipi-isis-types:isis_is_type3_t;
            default "level-2";
            description "Redist level";
        } // END of ipv6-level definition.

        leaf ipv6-metric-value  {
            type  uint32 {
                 range "0..16777215"  {
                    description "0..16777215:IS-IS default metric";
                 }
            }
            default "0";
            description "Use this attributes to redistribute routes from another protocol into
                        the ISIS routing table. With metric, metric-type, level and route-map
                        options.";
        } // END of ipv6-metric-value definition.

        leaf ipv6-metric-type  {
            type  ipi-isis-types:isis_metric_t;
            default "internal";
            description "Redist metric type";
        } // END of ipv6-metric-type definition.

        leaf ipv6-route-map  {
            type  string {
                length "0..1965";
                pattern "[^?' =,>|]*";
            }
            default "";
            description "Routemap name";
        } // END of ipv6-route-map definition.

    } // END of isis-ipv6-redist-config definition.
    grouping isis-summary-prefix-config {
        description
            "Configuration items for ISIS Summary Prefix";
        leaf prefix  {
            type  inet:ipv6-prefix;
            description "Use this attribute to configure the summary prefix to summarize IPv6
                        reachability information.";
        } // END of prefix definition.

        leaf level  {
            when " /ipi-isis:isis/ipi-isis:isis-instance/ipi-isis:address-family-ipv6/ipi-isis:summary-prefix/ipi-isis:config/ipi-isis:prefix ";
            type  ipi-isis-types:isis_summary_level_t;
            mandatory true;
            description "IS-IS instance level,(1|2|3)";
        } // END of level definition.

        leaf metric  {
            when " /ipi-isis:isis/ipi-isis:isis-instance/ipi-isis:address-family-ipv6/ipi-isis:summary-prefix/ipi-isis:config/ipi-isis:prefix ";
            type  uint8 {
                 range "1..63"  {
                    description "1..63:Metric Range";
                 }
            }
            description "Metric value";
        } // END of metric definition.

    } // END of isis-summary-prefix-config definition.
    grouping isis-mt-config {
        description
            "Configuration items for ISIS MT";
        leaf level  {
            type  ipi-isis-types:isis_multi_topology_level_type_t;
            description "Use this attribute to configure the ISIS MT";
        } // END of level definition.

    } // END of isis-mt-config definition.
    grouping isis-srv6-config {
        description
            "config attribute for SRv6 for SR Policies";
        leaf isisSRv6enable  {
            type  empty;
            mandatory true;
            description "";
        } // END of isisSRv6enable definition.

    } // END of isis-srv6-config definition.
    grouping locator-name-config {
        description
            "config attribute for SRv6 for SR Policies";
        leaf isisSRv6LocatorName  {
            type  string {
                length "1..1965";
                pattern "[^?' =,>|]+";
            }
            description "Locator name";
        } // END of isisSRv6LocatorName definition.

    } // END of locator-name-config definition.
    grouping isis-srv6-locator-lists-config {
        description
            "Locator";
        container locator-lists {
            when " /ipi-isis:isis/ipi-isis:isis-instance/ipi-isis:address-family-ipv6/ipi-isis:isis-srv6/ipi-isis:config/ipi-isis:isisSRv6enable ";
            description
                "SRv6 Locator List";

            list locator-list {
                key "isisSRv6LocatorName";
                description
                    "Properties of a locator list";
                leaf isisSRv6LocatorName  {
                    type  leafref {
                        path  "../config/isisSRv6LocatorName";
                    }
                    description "Locator name";
                } // END of isisSRv6LocatorName definition.

                container config {
                    description
                        "Config parameters for locator-list configuration";
                    uses locator-name-config;
                } // END of config-container definition.
                container state {
                    config false;
                    description
                        "";
                    uses locator-name-config;
                } // END of state-container definition.
            } // End of locator-list-list
        } // END of locator-lists-container definition.
    } // END of isis-srv6-locator-lists-config definition.
    grouping isis-distance-config {
        description
            "Configuration items for ISIS Distance";
        leaf system-id  {
            type  string {
                length "0..1965";
                pattern "[^?' =,>|]*";
            }
            description "System ID";
        } // END of system-id definition.

        leaf value  {
            type  uint8 {
                 range "1..255"  {
                    description "1..255:range";
                 }
            }
            mandatory true;
            description "Distance Value";
        } // END of value definition.

        leaf access-list-name  {
            when " /ipi-isis:isis/ipi-isis:isis-instance/ipi-isis:distance/ipi-isis:config/ipi-isis:value ";
            type  string {
                length "0..1965";
                pattern "[^?' =,>|]*";
            }
            default "";
            description "Use this attribute to set the administrative distance for specific
                        IPv4 routes.";
        } // END of access-list-name definition.

    } // END of isis-distance-config definition.
    grouping isis-lsp-overload-config {
        description
            "Configuration items for ISIS LSP Overlaod";
        leaf enabled  {
            type  empty;
            mandatory true;
            description "Use this attribute to set the overload-bit in self-LSPs. If the
                        overload-bit is set in LSPs, the router is not used as a transit
                        router during SPF calculation. This configuration causes a router to
                        update its own LSP with the overload bit set and causes the other
                        routers not to use this router as a transit or forwarding router. The
                        router continues to receive LSPs when the overload bit is set. If the
                        on-startup option is specified, the router sets the overload bit only
                        at startup, then clears the bit after the specified interval has
                        elapsed. If the on-startup option is specified using the wait-for-bgp
                        option, the overload bit is setup at startup, then the bit is cleared
                        after the BGP router signals it has finished converging or if the
                        router does not signal it has finished converging in 10 minutes. If
                        there is no BGP process running, the overload bit clears immediately.";
        } // END of enabled definition.

        leaf suppress-type  {
            type  ipi-isis-types:isis_suppress_t;
            description "Use this attributes to set the overload-bit in self-LSPs. If the
                        overload-bit is set in LSPs, the router is not used as a transit
                        router during SPF calculation. This configuration causes a router to
                        update its own LSP with the overload bit set and causes the other
                        routers not to use this router as a transit or forwarding router. The
                        router continues to receive LSPs when the overload bit is set. If the
                        on-startup option is specified, the router sets the overload bit only
                        at startup, then clears the bit after the specified interval has
                        elapsed. If the on-startup option is specified using the wait-for-bgp
                        option, the overload bit is setup at startup, then the bit is cleared
                        after the BGP router signals it has finished converging or if the
                        router does not signal it has finished converging in 10 minutes. If
                        there is no BGP process running, the overload bit clears immediately.";
        } // END of suppress-type definition.

        leaf set-bit-on-boot  {
            type  ipi-isis-types:isis_onstartup_t;
            description "Overload interval after reboot";
        } // END of set-bit-on-boot definition.

    } // END of isis-lsp-overload-config definition.
    grouping isis-af-ipv4-state {
        description
            "State items for ISIS AF IPv4";
        leaf existence-state  {
            type  uint8;
            description "SNMP variable";
        } // END of existence-state definition.

        leaf redistribute-update  {
            type  int32;
            description "Redistrubution timer argument";
        } // END of redistribute-update definition.

        leaf redistribute-timer-value  {
            type  string {
                length "1..1965";
                pattern "[^?' =,>|]+";
            }
            description "Redistribution last performed";
        } // END of redistribute-timer-value definition.

    } // END of isis-af-ipv4-state definition.
    grouping isis-af-ipv4-distribution-level-1-2-config {
        description
            "Configuration items for ISIS AF IPv4 level 1 to 2 Distribution";
        leaf enable  {
            type  empty;
            description "Use this attribute to redistribute reachability information from one
                        level to the other level. If an distribute-list name is given with
                        this command for an access list that does not exist, the routes are
                        still redistributed.";
        } // END of enable definition.

        leaf level1-acl  {
            type  string {
                length "1..1965";
                pattern "[^?' =,>|]+";
            }
            description "Use this attribute to redistribute reachability information from one
                        level to the other level. If an distribute-list name is given with
                        this command for an access list that does not exist, the routes are
                        still redistributed.";
        } // END of level1-acl definition.

    } // END of isis-af-ipv4-distribution-level-1-2-config definition.
    grouping isis-af-ipv4-distribution-level-2-1-config {
        description
            "Configuration items for ISIS AF IPv4 level 2 to 1 Distribution";
        leaf enable  {
            type  empty;
            description "Use this attribute to redistribute reachability information from one
                        level to the other level. If an distribute-list name is given with
                        this command for an access list that does not exist, the routes are
                        still redistributed.";
        } // END of enable definition.

        leaf level2-acl  {
            type  string {
                length "1..1965";
                pattern "[^?' =,>|]+";
            }
            description "Use this attribute to redistribute reachability information from one
                        level to the other level. If an distribute-list name is given with
                        this command for an access list that does not exist, the routes are
                        still redistributed.";
        } // END of level2-acl definition.

    } // END of isis-af-ipv4-distribution-level-2-1-config definition.
    grouping isis-af-ipv4-default-info-config {
        description
            "Configuration items for ISIS AF IPv4 Default Info";
        leaf originate  {
            type  ipi-isis-types:isis_origin_type_t;
            description "Use this attribute to originate reachability information to Default
                        destination into LSP.There is no default information in Level-2 domain
                        by default, while Level-1 router calculates default to L1L2 route
                        during SPF calculation. This command enables to originate default
                        route into Level-2 domain.";
        } // END of originate definition.

        leaf route-map-name  {
            when " /ipi-isis:isis/ipi-isis:isis-instance/ipi-isis:address-family-ipv4/ipi-isis:default-route-information/ipi-isis:config/ipi-isis:originate ";
            type  string {
                length "0..1965";
                pattern "[^?' =,>|]*";
            }
            default "";
            description "Route Map Name Attribute";
        } // END of route-map-name definition.

    } // END of isis-af-ipv4-default-info-config definition.
    grouping isis-af-ipv4-redistribution-config {
        description
            "Configuration items for ISIS AF IPv4 Redistribution";
        leaf protocol-type  {
            type  ipi-isis-types:isis_redistribute_t;
            description "Use this attribute to redistribute routes from another protocol into
                        the ISIS routing table.";
        } // END of protocol-type definition.

    } // END of isis-af-ipv4-redistribution-config definition.
    grouping isis-af-ipv4-redistribution-configurations-config {
        description
            "Configuration items for ISIS AF IPv4 Redistribution Configuration";
        leaf level  {
            type  ipi-isis-types:isis_is_type3_t;
            default "level-2";
            description "Level Redistribution";
        } // END of level definition.

        leaf metric-value  {
            type  uint32 {
                 range "0..16777215"  {
                    description "0..16777215:IS-IS default metric";
                 }
            }
            default "0";
            description "IS-IS metric";
        } // END of metric-value definition.

        leaf metric-type  {
            type  ipi-isis-types:isis_metric_t;
            default "internal";
            description "External metric type, (Internal|External)";
        } // END of metric-type definition.

        leaf route-map  {
            type  string {
                length "0..1965";
                pattern "[^?' =,>|]*";
            }
            default "";
            description "Name of route-map";
        } // END of route-map definition.

    } // END of isis-af-ipv4-redistribution-configurations-config definition.
    grouping isis-af-ipv4-summary-prefix-config {
        description
            "Configuration items for ISIS AF IPv4 Summary Prefix";
        leaf prefix  {
            type  inet:ipv4-prefix;
            description "Use this attribute to Summary Address to summarize IPv4 reachability
                        information.";
        } // END of prefix definition.

        leaf level  {
            when " /ipi-isis:isis/ipi-isis:isis-instance/ipi-isis:address-family-ipv4/ipi-isis:summary-address/ipi-isis:config/ipi-isis:prefix ";
            type  ipi-isis-types:isis_summary_level_t;
            mandatory true;
            description "IS-IS instance level";
        } // END of level definition.

        leaf metric  {
            when " /ipi-isis:isis/ipi-isis:isis-instance/ipi-isis:address-family-ipv4/ipi-isis:summary-address/ipi-isis:config/ipi-isis:prefix ";
            type  uint8 {
                 range "1..63"  {
                    description "1..63:Metric Range";
                 }
            }
            description "Metric value";
        } // END of metric definition.

    } // END of isis-af-ipv4-summary-prefix-config definition.
    grouping isis-af-ipv4-redist-isis-config {
        description
            "Configuration items for ISIS AF IPv4 Redist ISIS";
        leaf id  {
            type  string {
                length "1..1965";
                pattern "[^?' =,>|]+";
            }
            description "Instance ID";
        } // END of id definition.

    } // END of isis-af-ipv4-redist-isis-config definition.
    grouping isis-conf-mode-debug-config {
        description
            "Debug flags for configuration";
        leaf debug-options  {
            type  ipi-isis-types:isis_debug_t;
            description "Debug Configuration Flag";
        } // END of debug-options definition.

        leaf enable-hello-debug  {
            type  empty;
            description "Use this attribute to turn on debugging for ISIS hello.";
        } // END of enable-hello-debug definition.

        leaf-list interface-hello  {
            type  string {
                length "1..1965";
                pattern "[^?' =,>|]+";
            }
            description "Use this attribute to turn on debugging for ISIS Interface hello";
        } // END of interface-hello definition.

        leaf-list system-id-hello  {
            type  string {
                length "1..1965";
                pattern "[^?' =,>|]+";
            }
            description "Use this attribute to turn on debugging for ISIS SID hello";
        } // END of system-id-hello definition.

        leaf cspf  {
            if-feature feature-list:HAVE_ISIS_CSPF;
            type  ipi-isis-types:isis_cspf_debug_t;
            description "Use this attribute to enable CSPF debug logs.";
        } // END of cspf definition.

    } // END of isis-conf-mode-debug-config definition.
    grouping isis-terminal-mode-debug-state {
        description
            "Operational debug information for terminal mode";
        container terminal-debug {
            config false;
            description
                "Runtime attributes for terminal debug";
            leaf debug-options  {
                type  ipi-isis-types:isis_debug_t;
                description "Debug Terminal Flag";
            } // END of debug-options definition.

            leaf hello  {
                type  boolean;
                description "Use this attribute to turn on debugging for ISIS hello.";
            } // END of hello definition.

            leaf-list interface-hello  {
                type  string {
                    length "1..1965";
                    pattern "[^?' =,>|]+";
                }
                description "Use this attribute to turn on debugging for ISIS Interface hello";
            } // END of interface-hello definition.

            leaf-list system-id-hello  {
                type  string {
                    length "1..1965";
                    pattern "[^?' =,>|]+";
                }
                description "Use this attribute to turn on debugging for ISIS SID hello";
            } // END of system-id-hello definition.

            leaf cspf  {
                if-feature feature-list:HAVE_ISIS_CSPF;
                type  ipi-isis-types:isis_cspf_debug_t;
                description "Use this attribute to enable CSPF debug logs.";
            } // END of cspf definition.

        } // END of terminal-debug-container definition.
    } // END of isis-terminal-mode-debug-state definition.

    grouping  isis-grouping {
    description
        "IS-IS master for instance wide configurations";
    container isis {
        description
            "IS-IS master for instance wide configurations";

        list isis-instance {
        when " /ipi-isis:isis/ipi-isis:isis-instance/ipi-isis:config/ipi-isis:vrf-name ";
            key "instance";
            description
                "IS-IS structure";
            leaf instance  {
                type  leafref {
                    path  "../config/instance";
                }
                description "Use this attribute to initiate an ISIS routing instance.Configure at
                            least one NET to start routing.";
            } // END of instance definition.


            list partial-route-computation {
                key "minimum-delay maximum-delay";
                description
                    "This objectlist defines the ISIS PRC";
                leaf minimum-delay  {
                    type  leafref {
                        path  "../config/minimum-delay";
                    }
                    description "Minimum delay between receiving a change to PRC calculation in
                                milliseconds.Default value is 500";
                } // END of minimum-delay definition.

                leaf maximum-delay  {
                    type  leafref {
                        path  "../config/maximum-delay";
                    }
                    description "Maximum delay between receiving a change to PRC calculation in
                                milliseconds.Default value is 50000";
                } // END of maximum-delay definition.

                container config {
                    description
                        "This container defines the ISIS PRC configurations.";
                    uses isis-prc-config;
                } // END of config-container definition.
                container state {
                    config false;
                    description
                        "This container defines the ISIS PRC runtime information.";
                    uses isis-prc-config;
                } // END of state-container definition.
            } // End of partial-route-computation-list

            list metric {
                if-feature feature-list:HAVE_WIDE_METRIC;
                key "style level-number";
                max-elements 1;
                description
                    "This objectlist defines the ISIS Metric";
                leaf style  {
                    type  leafref {
                        path  "../config/style";
                    }
                    description "Use this attribute to configure the ISIS metric style";
                } // END of style definition.

                leaf level-number  {
                    type  leafref {
                        path  "../config/level-number";
                    }
                    description "Use this attribute to configure the ISIS metric style for particular
                                level";
                } // END of level-number definition.

                container config {
                    description
                        "This container defines the ISIS Metric configurations.";
                    uses isis-metric-config;
                } // END of config-container definition.
                container state {
                    config false;
                    description
                        "This container defines the ISIS Metric Operational parameters.";
                    uses isis-metric-config;
                } // END of state-container definition.
            } // End of metric-list

            list ipv4-route {
                key "destination-prefix";
                config false;
                description
                    "This container defines the ISIS Route";
                leaf destination-prefix  {
                    type  leafref {
                        path  "../state/destination-prefix";
                    }
                    description "Destination Prefix";
                } // END of destination-prefix definition.


                list nexthop {
                    key "nexthop-ip";
                    config false;
                    description
                        "This container defines the ISIS Route Next Hop";
                    leaf nexthop-ip  {
                        type  leafref {
                            path  "../state/nexthop-ip";
                        }
                        description "Prefix";
                    } // END of nexthop-ip definition.

                    container state {
                        config false;
                        description
                            "This container defines the ISIS Route Next Hop State";
                        uses isis-route-nh-state;
                    } // END of state-container definition.
                } // End of nexthop-list
                container state {
                    config false;
                    description
                        "This container defines the ISIS State";
                    uses isis-route-state;
                } // END of state-container definition.
            } // End of ipv4-route-list

            list ipv6-route {
                key "destination-prefix";
                config false;
                description
                    "This container defines the ISIS IPv6 Route";
                leaf destination-prefix  {
                    type  leafref {
                        path  "../state/destination-prefix";
                    }
                    description "Destination Prefix";
                } // END of destination-prefix definition.


                list nexthop {
                    key "nexthop-ip";
                    config false;
                    description
                        "This container defines the ISIS IPv6 Route Next Hop";
                    leaf nexthop-ip  {
                        type  leafref {
                            path  "../state/nexthop-ip";
                        }
                        description "Nexthop Prefix";
                    } // END of nexthop-ip definition.

                    container state {
                        config false;
                        description
                            "This container defines the ISIS IPv6 Route Next Hop State";
                        uses isis-ipv6-route-nh-state;
                    } // END of state-container definition.
                } // End of nexthop-list
                container state {
                    config false;
                    description
                        "This container defines the ISIS IPv6 State";
                    uses isis-ipv6-route-state;
                } // END of state-container definition.
            } // End of ipv6-route-list

            list distance {
                key "system-id";
                description
                    "ISIS Distance Attributes";
                leaf system-id  {
                    type  leafref {
                        path  "../config/system-id";
                    }
                    description "System ID";
                } // END of system-id definition.

                container config {
                    description
                        "Config Attributes for ISIS Distance";
                    uses isis-distance-config;
                } // END of config-container definition.
                container state {
                    config false;
                    description
                        "Operational Attributes for ISIS Distance";
                    uses isis-distance-config;
                } // END of state-container definition.
            } // End of distance-list
            container config {
                description
                    "This container defines the ISIS top configurations.";
                uses isis-mpls-traffic-engg-config;
                uses isis-global-config;
            } // END of config-container definition.
            container state {
                config false;
                description
                    "This container defines the ISIS top states.";
                container counters {
                    config false;
                    description
                        "This container defines the ISIS Adjacency Counters";
                    uses isis-adjacency-counter-state;
                } // END of counters-container definition.
                uses isis-global-state;
                uses isis-global-config;
                uses isis-mpls-traffic-engg-config;
            } // END of state-container definition.
            container vrf {
                config false;
                description
                    "This container defines the ISIS VRF";

                list igp-shortcut-lsp {
                    key "index";
                    config false;
                    description
                        "This objectlist defines the ISIS IGP shortcut LSP";
                    leaf index  {
                        type  leafref {
                            path  "../state/index";
                        }
                        description "Index";
                    } // END of index definition.

                    container state {
                        config false;
                        description
                            "This container defines the ISIS IGP shortcut LSP state";
                        uses isis-igp-shortcut-lsp-state;
                    } // END of state-container definition.
                } // End of igp-shortcut-lsp-list
            } // END of vrf-container definition.
            container area-authentication {
                description
                    "This container defines the ISIS Area Auth";
                container config {
                    presence "To configure area-password";
                    description
                        "This container defines the ISIS Area Auth configurations.";
                    uses isis-area-auth-config;
                } // END of config-container definition.
                container state {
                    config false;
                    description
                        "This container defines the ISIS Area Auth operational parameters.";
                    uses isis-area-auth-config;
                } // END of state-container definition.
            } // END of area-authentication-container definition.
            container network-entity-title {
                description
                    "To configure NET for an ISIS instance";
                container config {
                    description
                        "This container defines the ISIS NET configuration.";
                    uses isis-net-config;
                } // END of config-container definition.
                container state {
                    config false;
                    description
                        "This container defines the ISIS net operational parameter.";
                    uses isis-net-config;
                } // END of state-container definition.
            } // END of network-entity-title-container definition.
            container domain-authentication {
                description
                    "This container defines the ISIS Domain Auth";
                container config {
                    presence "To configure domain-password";
                    description
                        "This container defines the ISIS Area Domain configurations.";
                    uses isis-domain-auth-config;
                } // END of config-container definition.
                container state {
                    config false;
                    description
                        "This container defines the ISIS Area Domain operational parameters.";
                    uses isis-domain-auth-config;
                } // END of state-container definition.
            } // END of domain-authentication-container definition.
            container manual-area-addresses {
                description
                    "This container defines the ISIS Address Area";
                container state {
                    config false;
                    description
                        "This container defines the ISIS Address Area state";
                    uses isis-area-addr-state;
                } // END of state-container definition.
            } // END of manual-area-addresses-container definition.
            container receive-area-addresses {
                description
                    "This container defines the ISIS Recv Address Area";
                container state {
                    config false;
                    description
                        "This container defines the ISIS Recv Address Area state";
                    uses isis-recv-area-addr-state;
                } // END of state-container definition.
            } // END of receive-area-addresses-container definition.
            container timers {
                description
                    "This container defines the ISIS LSP Timers";
                container config {
                    description
                        "This container defines the ISIS LSP Timers configurations.";
                    uses isis-lsp-timers-config;
                } // END of config-container definition.
                container state {
                    config false;
                    description
                        "This container defines the ISIS LSP Timers Operational parameters.";
                    uses isis-lsp-timers-config;
                } // END of state-container definition.
            } // END of timers-container definition.
            container traffic-engineering {
                description
                    "This container defines the ISIS Traffic Engineering";
                container config {
                    description
                        "This container defines the ISIS TE Router ID configurations.";
                    uses isis-te-ipv4-router-id-config;
                    uses isis-te-ipv6-router-id-config;
                } // END of config-container definition.
                container state {
                    config false;
                    description
                        "This container defines the ISIS TE Router ID operational information.";
                    uses isis-te-ipv4-router-id-config;
                    uses isis-te-ipv6-router-id-config;
                } // END of state-container definition.
            } // END of traffic-engineering-container definition.
            container address-family-ipv6 {
                when " /ipi-isis:isis/ipi-isis:isis-instance/ipi-isis:address-family-ipv6/ipi-isis:config/ipi-isis:afi-name ";
                description
                    "This container defines the ISIS IPv6 Route";

                list redistribute-level-1-into-2 {
                    key "enable";
                    max-elements 1;
                    description
                        "This objectlist defines isis redistribution from level 1 into level 2";
                    leaf enable  {
                        type  leafref {
                            path  "../config/enable";
                        }
                        description "Use this attribute to redistribute reachability information from one
                                    level to the other level. If an distribute-list name is given with
                                    this command for an access list that does not exist, the routes are
                                    still redistributed.";
                    } // END of enable definition.

                    container config {
                        description
                            "This container defines configurations for isis redistribution from
                                    level 1 into level 2";
                        uses isis-af-ipv6-redist-1-2-config;
                    } // END of config-container definition.
                    container state {
                        config false;
                        description
                            "This container defines operational information for isis redistribution
                                    from level 1 into level 2";
                        uses isis-af-ipv6-redist-1-2-config;
                    } // END of state-container definition.
                } // End of redistribute-level-1-into-2-list

                list redistribute-level-2-into-1 {
                    key "enable";
                    max-elements 1;
                    description
                        "This objectlist defines isis redistribution from level 2 into level 1";
                    leaf enable  {
                        type  leafref {
                            path  "../config/enable";
                        }
                        description "Use this attribute to redistribute reachability information from one
                                    level to the other level. If an distribute-list name is given with
                                    this command for an access list that does not exist, the routes are
                                    still redistributed.";
                    } // END of enable definition.

                    container config {
                        description
                            "This container defines configurations for isis redistribution from
                                    level 2 into level 1";
                        uses isis-af-ipv6-redist-2-1-config;
                    } // END of config-container definition.
                    container state {
                        config false;
                        description
                            "This container defines operational information for isis redistribution
                                    from level 2 into level 1";
                        uses isis-af-ipv6-redist-2-1-config;
                    } // END of state-container definition.
                } // End of redistribute-level-2-into-1-list

                list default-route-information {
                    key "originate";
                    max-elements 1;
                    description
                        "This objectlist defines the ISIS Protocol Default Information
                                    Configurations and state information";
                    leaf originate  {
                        type  leafref {
                            path  "../config/originate";
                        }
                        description "Use this attribute to set originate reachability information to
                                    Default destination
                                    into LSP.There is no default information in Level-2 domain by default,
                                    while Level-1 router calculates default to L1L2 route during SPF
                                    calculation. This command enables to originate default route into
                                    Level-2 domain.";
                    } // END of originate definition.

                    container config {
                        description
                            "ISIS Protocol Default Information Configurations";
                        uses isis-af-ipv6-default-info-config;
                    } // END of config-container definition.
                    container state {
                        config false;
                        description
                            "ISIS Protocol Default Information operational information";
                        uses isis-af-ipv6-default-info-config;
                    } // END of state-container definition.
                } // End of default-route-information-list

                list redistribute {
                    key "ipv6-protocol-type";
                    description
                        "This objectlist defines the Redistribute List";
                    leaf ipv6-protocol-type  {
                        type  leafref {
                            path  "../config/ipv6-protocol-type";
                        }
                        description "Use this attribute to redistribute routes from another protocol into
                                    the ISIS routing table.";
                    } // END of ipv6-protocol-type definition.

                    container config {
                        description
                            "This container defines the ISIS Proto Redistribute Configurations";
                        uses isis-ipv6-proto-redist-config;
                        uses isis-ipv6-redist-config;
                    } // END of config-container definition.
                    container state {
                        config false;
                        description
                            "This container defines the ISIS Proto Redistribute Operational
                                    information";
                        uses isis-ipv6-proto-redist-config;
                        uses isis-ipv6-redist-config;
                    } // END of state-container definition.
                } // End of redistribute-list

                list summary-prefix {
                    key "prefix";
                    description
                        "This objectlist defines the Summary Prefix List";
                    leaf prefix  {
                        type  leafref {
                            path  "../config/prefix";
                        }
                        description "Use this attribute to configure the summary prefix to summarize IPv6
                                    reachability information.";
                    } // END of prefix definition.

                    container config {
                        description
                            "This container defines the ISIS Summary Prefix Configurations";
                        uses isis-summary-prefix-config;
                    } // END of config-container definition.
                    container state {
                        config false;
                        description
                            "This container defines the ISIS Summary Prefix operational information";
                        uses isis-summary-prefix-config;
                    } // END of state-container definition.
                } // End of summary-prefix-list

                list multi-topology {
                    if-feature feature-list:HAVE_MULTI_TOPOLOGY;
                    key "level";
                    max-elements 1;
                    description
                        "This objectlist defines the Multi-topology";
                    leaf level  {
                        type  leafref {
                            path  "../config/level";
                        }
                        description "Use this attribute to configure the ISIS Multi-topology";
                    } // END of level definition.

                    container config {
                        description
                            "This container defines the ISIS Multi topology configurations.";
                        uses isis-mt-config;
                    } // END of config-container definition.
                    container state {
                        config false;
                        description
                            "This container defines the ISIS Multi topology.";
                        uses isis-mt-config;
                    } // END of state-container definition.
                } // End of multi-topology-list
                container config {
                    presence "To enable address family ipv6";
                    description
                        "This container defines the ISIS AF IPv6 configurations";
                    uses isis-af-ipv6-config;
                } // END of config-container definition.
                container state {
                    config false;
                    description
                        "This container defines the ISIS AF IPv6 operational information";
                    uses isis-af-ipv6-config;
                } // END of state-container definition.
                container isis-srv6 {
                    if-feature feature-list:HAVE_SRV6;
                    description
                        "SRv6 container for segment routing";
                    container config {
                        presence "yes";
                        description
                            "Segment routing SRv6 configuration and other CLIs inside srv6";
                        uses isis-srv6-config;
                    } // END of config-container definition.
                    container state {
                        config false;
                        description
                            "Segment routing V6 runtime parameters";
                        uses isis-srv6-config;
                    } // END of state-container definition.
                    uses isis-srv6-locator-lists-config;
                } // END of isis-srv6-container definition.
            } // END of address-family-ipv6-container definition.
            container lsp-over-load {
                when " /ipi-isis:isis/ipi-isis:isis-instance/ipi-isis:lsp-over-load/ipi-isis:config/ipi-isis:enabled ";
                description
                    "set overload bit";
                container config {
                    presence "To enable LSP overload";
                    description
                        "LSP Overload Configurations";
                    uses isis-lsp-overload-config;
                } // END of config-container definition.
                container state {
                    config false;
                    description
                        "LSP Overload operational information";
                    uses isis-lsp-overload-config;
                } // END of state-container definition.
            } // END of lsp-over-load-container definition.
            container address-family-ipv4 {
                description
                    "IS-IS protocol IPV4";

                list redistribution-level-1-into-2 {
                    key "enable";
                    max-elements 1;
                    description
                        "This objectlist defines the ISIS Protocol Redistribution
                                    Configurations";
                    leaf enable  {
                        type  leafref {
                            path  "../config/enable";
                        }
                        description "Use this attribute to redistribute reachability information from one
                                    level to the other level. If an distribute-list name is given with
                                    this command for an access list that does not exist, the routes are
                                    still redistributed.";
                    } // END of enable definition.

                    container config {
                        description
                            "ISIS Protocol Default Information Configurations";
                        uses isis-af-ipv4-distribution-level-1-2-config;
                    } // END of config-container definition.
                    container state {
                        config false;
                        description
                            "ISIS Protocol Default Information Operational information";
                        uses isis-af-ipv4-distribution-level-1-2-config;
                    } // END of state-container definition.
                } // End of redistribution-level-1-into-2-list

                list redistribution-level-2-into-1 {
                    key "enable";
                    max-elements 1;
                    description
                        "This objectlist defines the ISIS Protocol Redistribution
                                    Configurations";
                    leaf enable  {
                        type  leafref {
                            path  "../config/enable";
                        }
                        description "Use this attribute to redistribute reachability information from one
                                    level to the other level. If an distribute-list name is given with
                                    this command for an access list that does not exist, the routes are
                                    still redistributed.";
                    } // END of enable definition.

                    container config {
                        description
                            "ISIS Protocol Default Information Configurations";
                        uses isis-af-ipv4-distribution-level-2-1-config;
                    } // END of config-container definition.
                    container state {
                        config false;
                        description
                            "ISIS Protocol Default Information Operational information";
                        uses isis-af-ipv4-distribution-level-2-1-config;
                    } // END of state-container definition.
                } // End of redistribution-level-2-into-1-list

                list default-route-information {
                    key "originate";
                    max-elements 1;
                    description
                        "This objectlist defines the ISIS Protocol Default Information
                                    Configurations and state information";
                    leaf originate  {
                        type  leafref {
                            path  "../config/originate";
                        }
                        description "Use this attribute to originate reachability information to Default
                                    destination into LSP.There is no default information in Level-2 domain
                                    by default, while Level-1 router calculates default to L1L2 route
                                    during SPF calculation. This command enables to originate default
                                    route into Level-2 domain.";
                    } // END of originate definition.

                    container config {
                        description
                            "ISIS Protocol Default Information Configurations";
                        uses isis-af-ipv4-default-info-config;
                    } // END of config-container definition.
                    container state {
                        config false;
                        description
                            "ISIS Protocol Default Information operational information";
                        uses isis-af-ipv4-default-info-config;
                    } // END of state-container definition.
                } // End of default-route-information-list

                list redistribute {
                    key "protocol-type";
                    description
                        "This objectlist defines configuration and state information for
                                    redistribution of routes from other protocols";
                    leaf protocol-type  {
                        type  leafref {
                            path  "../config/protocol-type";
                        }
                        description "Use this attribute to redistribute routes from another protocol into
                                    the ISIS routing table.";
                    } // END of protocol-type definition.

                    container config {
                        description
                            "ISIS Protocol Default Information Configurations";
                        uses isis-af-ipv4-redistribution-config;
                        uses isis-af-ipv4-redistribution-configurations-config;
                    } // END of config-container definition.
                    container state {
                        config false;
                        description
                            "ISIS Protocol Default Information state information";
                        uses isis-af-ipv4-redistribution-config;
                        uses isis-af-ipv4-redistribution-configurations-config;
                    } // END of state-container definition.
                } // End of redistribute-list

                list summary-address {
                    key "prefix";
                    description
                        "This objectlist contains config and state information related to
                                    summary-address";
                    leaf prefix  {
                        type  leafref {
                            path  "../config/prefix";
                        }
                        description "Use this attribute to Summary Address to summarize IPv4 reachability
                                    information.";
                    } // END of prefix definition.

                    container config {
                        description
                            "AF IPv4 Summary Prefix List";
                        uses isis-af-ipv4-summary-prefix-config;
                    } // END of config-container definition.
                    container state {
                        config false;
                        description
                            "AF IPv4 Summary Prefix List state information";
                        uses isis-af-ipv4-summary-prefix-config;
                    } // END of state-container definition.
                } // End of summary-address-list

                list redistribute-isis-instance {
                    key "id";
                    max-elements 1;
                    description
                        "This objectlist defines config and state information related to isis
                                    redistribuition";
                    leaf id  {
                        type  leafref {
                            path  "../config/id";
                        }
                        description "Instance ID";
                    } // END of id definition.

                    container config {
                        description
                            "AF IPv4 Redistribution Configurations";
                        uses isis-af-ipv4-redist-isis-config;
                        uses isis-af-ipv4-redistribution-configurations-config;
                    } // END of config-container definition.
                    container state {
                        config false;
                        description
                            "AF IPv4 Redistribution state information";
                        uses isis-af-ipv4-redist-isis-config;
                        uses isis-af-ipv4-redistribution-configurations-config;
                    } // END of state-container definition.
                } // End of redistribute-isis-instance-list
                container state {
                    config false;
                    description
                        "This container defines the ISIS Protocol State Information";
                    uses isis-af-ipv4-state;
                } // END of state-container definition.
            } // END of address-family-ipv4-container definition.
            uses isis-passive-interface-top;
            uses spf-level-grouping;
            uses level-grouping;
            uses level-runtime-grouping;
            uses cspf-grouping;
            uses ipv4-lfa-route-grouping;
            uses ipv6-lfa-route-grouping;
            uses fast-reroute-grouping;
            uses segment-routing-capability-grouping;
            uses segment-routing-mapping-server-ipv4-grouping;
            uses segment-routing-mapping-server-ipv6-grouping;
            uses segment-routing-grouping;
        } // End of isis-instance-list
        container debug {
            description
                "Debug Flags";
            container config {
                description
                    "Debug flags for configuration";
                uses isis-conf-mode-debug-config;
            } // END of config-container definition.
            container state {
                config false;
                description
                    "Debug flags state information";
                uses isis-conf-mode-debug-config;
                uses isis-terminal-mode-debug-state;
            } // END of state-container definition.
        } // END of debug-container definition.
        container state {
            config false;
            description
                "Notification state information";
            leaf-list host-name  {
                type  string {
                    length "1..1965";
                    pattern "[^?' =,>|]+";
                }
                description "Hostname";
            } // END of host-name definition.

            uses isis-notif-state;
        } // END of state-container definition.
        uses graceful-restart-grouping;
        uses interfaces-grouping;
    } // END of isis-container definition.
    } // END of isis-grouping definition.

    uses isis-grouping;

    rpc isis-restart-graceful {
        if-feature feature-list:HAVE_RESTART;
        description "Use this RPC to gracefully restart the IS-IS router.";
        input  {
            leaf grace-period  {
                type uint16 {
                    range "1..65535";
                }
                description "The time within which ISIS should come up";
            }
        }
    }

    rpc isis-clear-interface-counters {
        description "Use this attribute to clear interface counters. If you do not specify
                    a parameter, then counters for all interfaces are cleared.";
        input  {
            leaf name  {
                type string;
                description "Specify the Interface name for which counters should be reset";
            }
        }
    }

    rpc isis-clear-is-neighbors {
        description "Use this attribute to clear IS neighbor adjacencies.";
        input  {
            leaf system-id  {
                type string;
                mandatory true;
                description "Specify the system-id for which neighbourship has to be cleared";
            }
        }
    }

    rpc isis-clear-clns-neighbors {
        description "Use this attribute to clear CLNS neighbor adjacencies.";
    }

    rpc isis-clear-ip-route {
        description "Use this attribute to clear IPv4 routes.";
        input  {
            leaf instance  {
                type string;
                description "Specify for which instance we need to clear";
            }
            leaf ipv4-route  {
                type ipi-isis-types:isis_route_t;
                mandatory true;
                description "Specify for which route-type we need to clear";
            }
        }
    }

    rpc isis-clear-ipv6-route {
        description "Use this attribute to clear IPv6 routes.";
        input  {
            leaf instance  {
                type string;
                description "Specify for which instance we need to clear";
            }
            leaf ipv6-route  {
                type ipi-isis-types:isis_route_t;
                mandatory true;
                description "Specify for which route-type we need to clear";
            }
        }
    }

    rpc isis-process-clear {
        description "Use this attribute to restart ISIS processes. If you do not specify a
                    parameter, then all ISIS processes are restarted.";
        input  {
            leaf instance  {
                type string;
                mandatory true;
                description "Specify for which instance we need to clear";
            }
        }
    }

    rpc isis-clear-counters {
        description "Use this attribute to clear system-wide IS-IS counters
                    (IsisSystemCounterEntry in RFC 4444).";
    }

    rpc isis-clear-adjacency-all {
        description "Use this attribute to clear all isis adjacency.";
        input  {
            leaf adjacency-vrf-name  {
                type string;
                description "Specify for which vrf we need to clear adjacency";
            }
        }
    }

    rpc isis-process-clear-adjacency-all {
        description "Use this attribute to clear all isis adjacency to specified router.";
        input  {
            leaf tag-name  {
                type string;
                mandatory true;
                description "Specify for which instance we need to clear adjacency";
            }
            leaf adjacency-vrf-name  {
                type string;
                description "Specify for which vrf we need to clear adjacency";
            }
        }
    }

    rpc isis-process-clear-adjacency-interface {
        description "Use this attribute to clear isis adjacency with specific interface.";
        input  {
            leaf tag-name  {
                type string;
                mandatory true;
                description "Specify for which instance we need to clear adjacency";
            }
            leaf tag-if-name  {
                type string;
                description "Specify for which interface we need to clear adjacency";
            }
            leaf adjacency-vrf-name  {
                type string;
                description "Specify for which vrf we need to clear adjacency";
            }
        }
    }

    rpc isis-clear-adjacency-interface {
        description "Use this attribute to clear isis adjacency for specific router.";
        input  {
            leaf adjacency-if-name  {
                type string;
                description "Specify for which interface we need to clear adjacency";
            }
            leaf adjacency-vrf-name  {
                type string;
                description "Specify for which vrf we need to clear adjacency";
            }
        }
    }

    rpc isis-process-clear-adjacency-system-id {
        description "Use this attribute to clear isis adjacency for specific system-id.";
        input  {
            leaf tag-name  {
                type string;
                mandatory true;
                description "Specify for which instance we need to clear adjacency";
            }
            leaf tag-system-id  {
                type ipi-isis-types:isis_systemid_t;
                mandatory true;
                description "Specify for which system-id we need to clear adjacency";
            }
            leaf tag-vrf-name  {
                type string;
                description "Specify for which vrf we need to clear adjacency";
            }
        }
    }

    rpc isis-clear-adjacency-system-id {
        description "Use this attribute to clear isis adjacency for specific system-id.";
        input  {
            leaf adjacency-system-id  {
                type ipi-isis-types:isis_systemid_t;
                mandatory true;
                description "Specify for which system-id we need to clear adjacency";
            }
            leaf adjacency-vrf-name  {
                type string;
                description "Specify for which vrf we need to clear adjacency";
            }
        }
    }

    rpc isis-restart-snmp {
        description "Use this attribute to restart SNMP in Intermediate System to
                    Intermediate System (IS-IS)";
    }

    rpc isis-debug-all-on {
        description "Use this RPC to       enable debug all ISIS";
    }

    rpc isis-debug-all-off {
        description "Use this RPC to       disable debug all ISIS";
    }

    rpc isis-debug-on {
        description "Use this RPC to enable debug on ISIS";
        input  {
            leaf debug-options  {
                type ipi-isis-types:isis_debug_t;
                mandatory true;
                description "Use this command to turn on, ISIS debugging at various levels.";
            }
        }
    }

    rpc isis-debug-off {
        description "Use this RPC to disable debug on ISIS";
        input  {
            leaf debug-options  {
                type ipi-isis-types:isis_debug_t;
                mandatory true;
                description "Use this command to turn off, ISIS debugging at various levels.";
            }
        }
    }

    rpc isis-debug-hello-on {
        description "Use this RPC to enable debug on ISIS hello messages.";
    }

    rpc isis-debug-hello-off {
        description "Use this RPC to disable debug on ISIS hello messages.";
    }

    rpc isis-debug-interface-hello-on {
        description "Use this RPC to enable debug on ISIS hello messages for an interface.";
        input  {
            leaf interface  {
                type string;
                mandatory true;
                description "Use this attribute to turn on debugging for ISIS Interface hello";
            }
        }
    }

    rpc isis-debug-interface-hello-off {
        description "Use this RPC to disable debug on ISIS hello messages for an interface.";
        input  {
            leaf interface  {
                type string;
                mandatory true;
                description "Use this attribute to turn off debugging for ISIS Interface hello";
            }
        }
    }

    rpc isis-debug-system-id-hello-on {
        description "Use this RPC to enable debug on ISIS SID hello messages.";
        input  {
            leaf system-id  {
                type string;
                mandatory true;
                description "Use this attribute to turn on debugging for ISIS SID hello";
            }
        }
    }

    rpc isis-debug-system-id-hello-off {
        description "Use this RPC to disable debug on ISIS SID hello messages.";
        input  {
            leaf system-id  {
                type string;
                mandatory true;
                description "Use this attribute to turn off debugging for ISIS SID hello";
            }
        }
    }

    rpc isis-undebug {
        description "Use this RPC to disable debug on ISIS.";
        input  {
            leaf debug-options  {
                type ipi-isis-types:isis_debug_t;
                mandatory true;
                description "Use this command to turn off, ISIS debugging at various levels.";
            }
        }
    }

    rpc isis-undebug-all {
        description "Use this RPC to disable debug on ISIS.";
    }

    rpc isis-all-undebug {
        description "Use this RPC to disable debug on ISIS.";
    }

    rpc isis-all-debug-off {
        description "Use this RPC to disable debug on ISIS.";
    }

    rpc isis-undebug-hello {
        description "Use this RPC to disable debug on ISIS hello messages.";
    }

    rpc isis-undebug-interface-hello {
        description "Use this RPC to disable debug on ISIS hello messages for an interface.";
        input  {
            leaf interface  {
                type string;
                mandatory true;
                description "Use this attribute to turn off debugging for ISIS Interface hello";
            }
        }
    }

    rpc isis-undebug-hello-system-id {
        description "Use this RPC to disable debug on ISIS SID hello messages.";
        input  {
            leaf system-id  {
                type string;
                mandatory true;
                description "Use this attribute to turn off debugging for ISIS SID hello";
            }
        }
    }

    rpc isis-debug-cspf-on {
        description "Use this RPC to enable debug on ISIS CSPF events.";
        input  {
            leaf cspf-debug  {
                type ipi-isis-types:isis_cspf_debug_t;
                mandatory true;
                description "";
            }
        }
    }

    rpc isis-debug-cspf-off {
        description "Use this RPC to disable debug on ISIS CSPF events.";
        input  {
            leaf cspf-debug  {
                type ipi-isis-types:isis_cspf_debug_t;
                mandatory true;
                description "";
            }
        }
    }

    rpc isis-undebug-cspf {
        description "Use this RPC to disable debug on ISIS CSPF events.";
        input  {
            leaf cspf-debug  {
                type ipi-isis-types:isis_cspf_debug_t;
                mandatory true;
                description "";
            }
        }
    }

    notification isis-database-overload {

        description "This notification is sent when an IS-IS instance overload state changes..";

        // severity "MAJOR";
        // eventClass "STATE";
        leaf overload {
            type ipi-isis-types:isis_overload_state_t;
        description
            "New overload state of the IS-IS instance";
        }
    }

    notification isis-lsp-too-large {

        description "This notification is sent when we attempt to propagate an LSP that is larger than the dataLinkBlockSize (ISO10589) for the circuit.The notification generation must be throttled with at least 5 seconds between successive notifications..";

        // severity "MINOR";
        // eventClass "STATE";
        leaf lsp-identifier {
            type  string;
        description
            "LSP ID";
        }

        leaf pdu-length {
            type  uint32;
        description
            "Size of the LSP PDU";
        }
    }

    notification isis-corrupted-lsp-detected {

        description "This notification is sent when we find that an LSP that was stored in memory has become corrupted..";

        // severity "MAJOR";
        // eventClass "STATE";
        leaf lsp-identifier {
            type  string;
        description
            "LSP ID";
        }
    }

    notification isis-attempt-to-exceed-max-sequence {

        description "This notification is sent when the system wraps the 32-bit sequence counter of an LSP..";

        // severity "MINOR";
        // eventClass "STATE";
        leaf lsp-identifier {
            type  string;
        description
            "LSP ID";
        }
    }

    notification isis-id-len-mismatch {

        description "This notification is sent when we receive a PDU with a different value for the system-id length.The notification generation must be throttled with at least 5 seconds between successive notifications..";

        // severity "MINOR";
        // eventClass "STATE";
        leaf pdu-field-len {
            type  uint8;
        description
            "Size of the ID length in the received PDU";
        }

        leaf raw-pdu {
            type  string;
        description
            "Received raw PDU";
        }
    }

    notification isis-max-area-addresses-mismatch {

        description "This notification is sent when we receive a PDU with a different value for the Maximum Area Addresses.The notification generation must be throttled with at least 5 seconds between successive notifications..";

        // severity "MINOR";
        // eventClass "STATE";
        leaf max-area-addresses {
            type  uint8;
        description
            "Received number of supported areas";
        }

        leaf raw-pdu {
            type  string;
        description
            "Received raw PDU";
        }
    }

    notification isis-own-lsp-purge {

        description "This notification is sent when the system receives a PDU with its own system-id and zero age..";

        // severity "MINOR";
        // eventClass "STATE";
        leaf lsp-identifier {
            type  string;
        description
            "LSP ID";
        }
    }

    notification isis-sequence-number-skipped {

        description "This notification is sent when the system receives a PDU with its own system-id and different contents. The system has to originate the LSP with a higher sequence number..";

        // severity "MINOR";
        // eventClass "STATE";
        leaf lsp-identifier {
            type  string;
        description
            "LSP ID";
        }
    }

    notification isis-authentication-type-failure {

        description "This notification is sent when the system receives a PDU with the wrong authentication type field.The notification generation must be throttled with at least 5 seconds between successive notifications..";

        // severity "MINOR";
        // eventClass "STATE";
        leaf raw-pdu {
            type  string;
        description
            "Received raw PDU";
        }
    }

    notification isis-authentication-failure {

        description "This notification is sent when the system receives a PDU with the wrong authentication information.The notification generation must be throttled..";

        // severity "MINOR";
        // eventClass "STATE";
        leaf raw-pdu {
            type  string;
        description
            "Received raw PDU";
        }
    }

    notification isis-version-skew {

        description "This notification is sent when the system receives a PDU with a different protocol version number.The notification generation must be throttled with at least 5 seconds between successive notifications..";

        // severity "MINOR";
        // eventClass "STATE";
        leaf protocol-version {
            type  uint8;
        description
            "Protocol version received in the PDU";
        }

        leaf raw-pdu {
            type  string;
        description
            "Received raw PDU";
        }
    }

    notification isis-area-mismatch {

        description "This notification is sent when the system receives a Hello PDU from an IS that does not share any area address. The notification generation must be throttled with at least 5 seconds between successive notifications..";

        // severity "MINOR";
        // eventClass "STATE";
        leaf raw-pdu {
            type  string;
        description
            "Received raw PDU";
        }
    }

    notification isis-rejected-adjacency {

        description "This notification is sent when the system receives a Hello PDU from an IS but does not establish an adjacency for some reason. The notification generation must be throttled with at least 5 seconds between successive notifications..";

        // severity "MINOR";
        // eventClass "STATE";
        leaf raw-pdu {
            type  string;
        description
            "Received raw PDU";
        }

        leaf reason {
            type  string;
        description
            "string describing the reason";
        }
    }

    notification isis-protocols-supported-mismatch {

        description "This notification is sent when the system receives a non-pseudonode LSP that has no matching protocols supported. The notification generation must be throttled with at least 5 seconds between successive notifications..";

        // severity "MINOR";
        // eventClass "STATE";
        leaf raw-pdu {
            type  string;
        description
            "Received raw PDU";
        }

        leaf protocols {
            type  uint8;
        description
            "List of protocols supported by the remote system";
        }
    }

    notification isis-lsp-error-detected {

        description "This notification is sent when the system receives an LSP with a parse error. The notification generation must be throttled with at least 5 seconds between successive notifications..";

        // severity "MINOR";
        // eventClass "STATE";
        leaf lsp-identifier {
            type  string;
        description
            "LSP ID";
        }

        leaf raw-pdu {
            type  string;
        description
            "Received raw PDU";
        }

        leaf error-offset {
            type  uint32;
        description
            "If the problem is a malformed TLV, the error-offset points to the
                    start of the TLV. If the problem is with the LSP header, the
                    error-offset points to the errant byte";
        }

        leaf tlv-type {
            type  uint8;
        description
            "If the problem is a malformed TLV, the tlv-type is set to the type
                    value of the suspicious TLV. Otherwise, this leaf is not presen";
        }
    }

    notification isis-segment-routing-index-out-of-range {

        description "SRGB range.";

        // severity "MAJOR";
        // eventClass "STATE";
        leaf global-block-base {
            type  int32;
        description
            "Start ID";
        }

        leaf global-block-range {
            type  int32;
        description
            "End ID";
        }

        leaf received-index {
            type  uint32;
        description
            "Index";
        }

        leaf routing-protocol {
            type  string;
        description
            "Module Name";
        }
    }

}

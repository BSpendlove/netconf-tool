/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ospfv3-types.yang
*
*/

module ipi-ospfv3-types {

    yang-version 1.1;

    namespace   "http://www.ipinfusion.com/yang/ocnos/ipi-ospfv3-types";

    prefix "ipi-ospfv3-types";

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 OSPFv3 types";


    revision "2021-11-17" {
        description "Added passive mode type";
        reference " 0.1.6.";
    }

    revision "2021-09-03" {
        description "Update descriptions of attribute";
        reference " 0.1.5.";
    }

    revision "2021-08-19" {
        description "OSPFv3 string type max length updated to 254";
        reference " 0.1.4.";
    }

    revision "2021-08-13" {
        description "Added debug packet options type";
        reference " 0.1.3.";
    }

    revision "2021-07-26" {
        description "Notification types support";
        reference " 0.1.2.";
    }

    revision "2021-07-05" {
        description "Added ls-metric-type datatype";
        reference " 0.1.1.";
    }

    revision "2021-06-17" {
        description "Restructured module in accordance with OpenConfig style";
        reference " 0.1.0.";
    }



    typedef  ospfv3_string_t {
        type string {
            length 0..254;
            pattern "[^?' =,>|]*";
        }
        description "type definition for OSPFV3_STRING_T";
    }

    typedef  ospfv3_abr_type_t {
        type enumeration {
            enum standard {
                value 1;
                description "Standard behavior (RFC2328)";
            }
            enum cisco {
                value 2;
                description "Alternative ABR using Cisco implementation (RFC3509)";
            }
            enum ibm {
                value 3;
                description "Alternative ABR using IBM implementation (RFC3509)";
            }
        }
        description "type definition for OSPFV3_ABR_TYPE_T";
    }

    typedef  ospfv3_log_adj_opt_t {
        type enumeration {
            enum brief {
                value 0;
                description "Log changes in adjacency state";
            }
            enum detail {
                value 1;
                description "Log all state changes";
            }
        }
        description "type definition for OSPFV3_LOG_ADJ_OPT_T";
    }

    typedef  ospfv3_frr_tie_break_method_t {
        type enumeration {
            enum primary-path {
                value 20;
                description "Prefer backup path from ECMP set \n\t     *Default value is 20\n";
            }
            enum node-protecting {
                value 30;
                description "Prefer node protecting backup path \n\t     *Default value is 30\n";
            }
            enum interface-disjoint {
                value 60;
                description "Prefer link protecting backup path \n\t     *Default value is 60\n";
            }
            enum broadcast-interface-disjoint {
                value 70;
                description "Prefer broadcast link protecting backup path \n\t\t\t        *Default value is 70\n";
            }
            enum downstream-path {
                value 90;
                description "Prefer backup path from downstream \n\t     *Default value is 90\n";
            }
            enum secondary-path {
                value 255;
                description "Prefer non-ECMP backup path \n\t\t\t        *Default value is 255\n";
            }
        }
        description "type definition for OSPFV3_FRR_TIE_BREAK_METHOD_T";
    }

    typedef  ospfv3_cspf_tie_break_method_t {
        type enumeration {
            enum random {
                value 0;
                description "Random";
            }
            enum most-fill {
                value 1;
                description "Most fill";
            }
            enum least-fill {
                value 2;
                description "Least fill";
            }
        }
        description "type definition for OSPFV3_CSPF_TIE_BREAK_METHOD_T";
    }

    typedef  ospfv3_metric_type_t {
        type enumeration {
            enum 1 {
                value 1;
                description "Set OSPFv3 External Type 1 metrics";
            }
            enum 2 {
                value 2;
                description "Set OSPFv3 External Type 2 metrics";
            }
        }
        description "type definition for OSPFV3_METRIC_TYPE_T";
    }

    typedef  ospfv3_af_route_source_type_t {
        type enumeration {
            enum kernel {
                value 1;
                description "Kernel routes";
            }
            enum connected {
                value 2;
                description "Connected";
            }
            enum static {
                value 3;
                description "Static routes";
            }
            enum rip {
                value 4;
                description "Routing Information Protocol (RIP)";
            }
            enum bgp {
                value 8;
                description "Border Gateway Protocol (BGP)";
            }
            enum isis {
                value 9;
                description "ISO IS-IS";
            }
        }
        description "type definition for OSPFV3_AF_ROUTE_SOURCE_TYPE_T";
    }

    typedef  ospfv3_route_source_type_t {
        type enumeration {
            enum kernel {
                value 1;
                description "Kernel routes";
            }
            enum connected {
                value 2;
                description "Connected";
            }
            enum static {
                value 3;
                description "Static routes";
            }
            enum rip {
                value 5;
                description "Routing Information Protocol (RIPng)";
            }
            enum bgp {
                value 8;
                description "Border Gateway Protocol (BGP)";
            }
            enum isis {
                value 9;
                description "ISO IS-IS";
            }
        }
        description "type definition for OSPFV3_ROUTE_SOURCE_TYPE_T";
    }

    typedef  ospfv3_area_t {
        type union {
            type uint32 {
                range "0..4294967295";

            }
            type inet:ipv4-address {

            }
        }
        description "type definition for OSPFV3_AREA_T";
    }

    typedef  ospfv3_translator_role_t {
        type enumeration {
            enum always {
                value 1;
                description "Always translate NSSA-LSA to Type-5 LSA";
            }
            enum candidate {
                value 2;
                description "Translate NSSA-LSA to Type-5 LSA if router is elected (default)";
            }
        }
        description "type definition for OSPFV3_TRANSLATOR_ROLE_T";
    }

    typedef  ospfv3_network_type_t {
        type enumeration {
            enum point-to-point {
                value 1;
                description "OSPF point-to-point network";
            }
            enum broadcast {
                value 2;
                description "OSPF broadcast multi-access network";
            }
            enum non-broadcast {
                value 3;
                description "OSPF NBMA network";
            }
            enum point-to-multipoint {
                value 4;
                description "OSPF point-to-multipoint network";
            }
            enum point-to-multipoint-non-broadcast {
                value 5;
                description "OSPF point-to-multipoint NBMA network,non-broadcast point-to-multipoint network";
            }
        }
        description "type definition for OSPFV3_NETWORK_TYPE_T";
    }

    typedef  ospfv3_path_type_t {
        type enumeration {
            enum Connected {
                value 0;
                description "Connected";
            }
            enum IntraArea {
                value 1;
                description "IntraArea";
            }
            enum InterArea {
                value 2;
                description "InterArea";
            }
            enum External {
                value 3;
                description "External";
            }
            enum Discard {
                value 4;
                description "Discard";
            }
        }
        description "type definition for OSPFV3_PATH_TYPE_T";
    }

    typedef  ospfv3_path_flags_t {
        type enumeration {
            enum Type2 {
                value 1;
                description "Type2";
            }
            enum ABR {
                value 2;
                description "ABR";
            }
            enum ASBR {
                value 3;
                description "ASBR";
            }
            enum RangeMatched {
                value 4;
                description "RangeMatched";
            }
        }
        description "type definition for OSPFV3_PATH_FLAGS_T";
    }

    typedef  ospfv3_link_status_t {
        type enumeration {
            enum up {
                value 1;
                description "Vlink Status is up";
            }
            enum down {
                value 2;
                description "Vlink Status is down";
            }
        }
        description "type definition for OSPFV3_LINK_STATUS_T";
    }

    typedef  ospfv3_interface_admin_state_t {
        type enumeration {
            enum up {
                value 0;
                description "Admin State UP";
            }
            enum down {
                value 1;
                description "Admin State DOWN";
            }
            enum administratively-down {
                value 2;
                description "Admin State ADMINISTRATIVELY DOWN";
            }
        }
        description "type definition for OSPFV3_INTERFACE_ADMIN_STATE_T";
    }

    typedef  ospfv3_interface_state_t {
        type enumeration {
            enum DependUpon {
                value 0;
                description "DependUpon";
            }
            enum Down {
                value 1;
                description "Down";
            }
            enum Loopback {
                value 2;
                description "Loopback";
            }
            enum Waiting {
                value 3;
                description "Waiting";
            }
            enum Point-To-Point {
                value 4;
                description "Point-To-Point";
            }
            enum DROther {
                value 5;
                description "DROther";
            }
            enum Backup {
                value 6;
                description "Backup";
            }
            enum DR {
                value 7;
                description "DR";
            }
        }
        description "type definition for OSPFV3_INTERFACE_STATE_T";
    }

    typedef  ospfv3_passive_mode_t {
        type enumeration {
            enum disable {
                value 0;
                description "Disable passive interface";
            }
            enum enable {
                value 1;
                description "Enable passive interface";
            }
        }
        description "type definition for OSPFV3_PASSIVE_MODE_T";
    }

    typedef  ospfv3_debug_event_t {
        type bits {
            bit abr {
                position 0;
                description "OSPFv3 ABR events";
            }
            bit asbr {
                position 1;
                description "OSPFv3 ASBR events ";
            }
            bit vlink {
                position 2;
                description "OSPFv3 Virtual-Link events";
            }
            bit os {
                position 3;
                description "OSPFv3 OS interaction events ";
            }
            bit router {
                position 4;
                description "Other router events ";
            }
            bit nssa {
                position 5;
                description "OSPFv3 NSSA events ";
            }
        }
        description "type definition for OSPFV3_DEBUG_EVENT_T";
    }

    typedef  ospfv3_debug_ifsm_t {
        type bits {
            bit status {
                position 0;
                description "IFSM status Information";
            }
            bit events {
                position 1;
                description "IFSM events Information";
            }
            bit timers {
                position 2;
                description "IFSM Timer Information";
            }
        }
        description "type definition for OSPFV3_DEBUG_IFSM_T";
    }

    typedef  ospfv3_debug_lsa_t {
        type bits {
            bit generate {
                position 0;
                description "LSA Generation";
            }
            bit flooding {
                position 1;
                description "LSA Flooding";
            }
            bit install {
                position 2;
                description "LSA Installation";
            }
            bit refresh {
                position 3;
                description "LSA Refreshment";
            }
            bit maxage {
                position 4;
                description "LSA MaxAge processing";
            }
        }
        description "type definition for OSPFV3_DEBUG_LSA_T";
    }

    typedef  ospfv3_debug_nfsm_t {
        type bits {
            bit status {
                position 0;
                description "NFSM status Information";
            }
            bit events {
                position 1;
                description "NFSM events Information";
            }
            bit timers {
                position 2;
                description "NFSM Timer Information";
            }
        }
        description "type definition for OSPFV3_DEBUG_NFSM_T";
    }

    typedef  ospfv3_debug_nsm_t {
        type bits {
            bit interface {
                position 0;
                description "NSM interface ";
            }
            bit redistribute {
                position 1;
                description "NSM redistribute ";
            }
        }
        description "type definition for OSPFV3_DEBUG_NSM_T";
    }

    typedef  ospfv3_debug_packet_options_t {
        type bits {
            bit send {
                position 0;
                description "Packet sent";
            }
            bit recv {
                position 1;
                description "Packet received";
            }
            bit detail {
                position 2;
                description "Detail information";
            }
        }
        description "type definition for OSPFV3_DEBUG_PACKET_OPTIONS_T";
    }

    typedef  ospfv3_debug_rib_t {
        type bits {
            bit interface {
                position 0;
                description "NSM interface ";
            }
            bit redistribute {
                position 1;
                description "NSM redistribute ";
            }
        }
        description "type definition for OSPFV3_DEBUG_RIB_T";
    }

    typedef  ospfv3_debug_route_t {
        type bits {
            bit spf {
                position 0;
                description "SPF calculation information";
            }
            bit ia {
                position 1;
                description "Inter-Area route calculation information";
            }
            bit ase {
                position 2;
                description "External route calculation information";
            }
            bit install {
                position 3;
                description "Route installation information";
            }
        }
        description "type definition for OSPFV3_DEBUG_ROUTE_T";
    }

    typedef  ospfv3_prefix_options_t {
        type bits {
            bit NU {
                position 0;
                description "No unicast";
            }
            bit LA {
                position 1;
                description "Local address";
            }
            bit MC {
                position 2;
                description "Multicast address";
            }
            bit P {
                position 3;
                description "Propagate (NSSA)";
            }
        }
        description "type definition for OSPFV3_PREFIX_OPTIONS_T";
    }

    typedef  ospfv3_ls_options_t {
        type bits {
            bit V6 {
                position 0;
                description "IPv6 forwarding";
            }
            bit E {
                position 1;
                description "External routing";
            }
            bit MC {
                position 2;
                description "Multicast forwarding";
            }
            bit N {
                position 3;
                description "Type-7(NSSA) LSA";
            }
            bit R {
                position 4;
                description "Forwarding (Any Protocol)";
            }
            bit DC {
                position 5;
                description "Demand Circuit handling";
            }
            bit AF {
                position 8;
                description "Address Family";
            }
        }
        description "type definition for OSPFV3_LS_OPTIONS_T";
    }

    typedef  ospfv3_router_properties_t {
        type bits {
            bit B {
                position 0;
                description "-";
            }
            bit E {
                position 1;
                description "-";
            }
            bit V {
                position 2;
                description "-";
            }
            bit W {
                position 3;
                description "-";
            }
            bit NT {
                position 4;
                description "-";
            }
        }
        description "type definition for OSPFV3_ROUTER_PROPERTIES_T";
    }

    typedef  ospfv3_link_metric_type_t {
        type enumeration {
            enum null {
                value 0;
                description "null";
            }
            enum point-to-point {
                value 1;
                description "Another Router (point-to-point)";
            }
            enum transit-network {
                value 2;
                description "Transit Network";
            }
            enum reserved {
                value 3;
                description "(Reserved)";
            }
            enum virtual-link {
                value 4;
                description "Virtual Link";
            }
        }
        description "type definition for OSPFV3_LINK_METRIC_TYPE_T";
    }

    typedef  ospfv3_ls_type_t {
        type enumeration {
            enum Unknown {
                value 0;
                description "Type Unknown";
            }
            enum Router-LSA {
                value 1;
                description "Type Router";
            }
            enum Network-LSA {
                value 2;
                description "Type Network";
            }
            enum Inter-Area-Prefix-LSA {
                value 3;
                description "Type Inter-Area-Prefix-LSA";
            }
            enum Inter-Area-Router-LSA {
                value 4;
                description "Type Inter-Area-Router-LSA";
            }
            enum AS-external-LSA {
                value 5;
                description "Type AS-external-LSA";
            }
            enum Group-Membership-LSA {
                value 6;
                description "Type Group-Membership-LSA";
            }
            enum NSSA-external-LSA {
                value 7;
                description "Type NSSA-external-LSA";
            }
            enum Link-LSA {
                value 8;
                description "Type Link-LSA";
            }
            enum Intra-Area-Prefix-LSA {
                value 9;
                description "Type Intra-Area-Prefix-LSA";
            }
            enum Intra-Area-Te-LSA {
                value 10;
                description "Type Intra-Area-Te-LSA";
            }
            enum Grace-LSA {
                value 11;
                description "Type Grace-LSA";
            }
        }
        description "type definition for OSPFV3_LS_TYPE_T";
    }

    typedef  ospfv3_ls_metric_type_t {
        type enumeration {
            enum 1 {
                value 1;
                description "Comparable directly to link state metric";
            }
            enum 2 {
                value 2;
                description "Larger than any link state path";
            }
        }
        description "type definition for OSPFV3_LS_METRIC_TYPE_T";
    }

    typedef  ospfv3_config_error_type_t {
        type enumeration {
            enum bad-version {
                value 1;
                description "Bad version";
            }
            enum area-mismatch {
                value 2;
                description "Area mismatch";
            }
            enum unknown-nbma-neighbor {
                value 3;
                description "Unknown NBMA neighbor";
            }
            enum unknown-virtual-neighbor {
                value 4;
                description "Unknown virtual neighbor";
            }
            enum auth-type-mismatch {
                value 5;
                description "Authentication type mismatch";
            }
            enum auth-failure {
                value 6;
                description "Authentication failure";
            }
            enum netmask-mismatch {
                value 7;
                description "Network mask mismatch";
            }
            enum hello-interval-mismatch {
                value 8;
                description "Hello interval mismatch";
            }
            enum dead-interval-mismatch {
                value 9;
                description "Dead interval mismatch";
            }
            enum option-mismatch {
                value 10;
                description "Option mismatch";
            }
            enum mtu-mismatch {
                value 11;
                description "MTU mismatch";
            }
            enum duplicate-router-id {
                value 12;
                description "Duplicated router ID";
            }
            enum no-error {
                value 13;
                description "No error";
            }
        }
        description "type definition for OSPFV3_CONFIG_ERROR_TYPE_T";
    }

    typedef  ospfv3_packet_type_t {
        type enumeration {
            enum hello {
                value 1;
                description "OSPF Hello";
            }
            enum db-desription {
                value 2;
                description "OSPF Database Description";
            }
            enum ls-request {
                value 3;
                description "OSPF Link State Request";
            }
            enum ls-update {
                value 4;
                description "OSPF Link State Update";
            }
            enum ls-ack {
                value 5;
                description "OSPF Link State Acknowledgment";
            }
        }
        description "type definition for OSPFV3_PACKET_TYPE_T";
    }

    typedef  ospfv3_neighbor_state_change_t {
        type enumeration {
            enum down {
                value 1;
                description "Down";
            }
            enum attempt {
                value 2;
                description "Attempt";
            }
            enum init {
                value 3;
                description "Init";
            }
            enum two-way {
                value 4;
                description "Two Way";
            }
            enum exchange-start {
                value 5;
                description "Exchange Start";
            }
            enum exchange {
                value 6;
                description "Exchange";
            }
            enum loading {
                value 7;
                description "Loading";
            }
            enum full {
                value 8;
                description "Full";
            }
        }
        description "type definition for OSPFV3_NEIGHBOR_STATE_CHANGE_T";
    }

}

module ipi-oc-terminal-device-deviations {
    namespace "http://www.ipinfusion.com/yang/ocnos/ipi-oc-terminal-device-deviations";
    prefix "ipi-oc-terminal-device-deviations";

    import openconfig-platform {
        prefix oc-platf;
    }

    import openconfig-terminal-device {
        prefix oc-opt-term;
    }

    revision "2021-12-22" {
        description
          "Add a deviation for pre-fec-ber and post-fec-ber.";
    }

    revision "2021-09-24" {
        description
          "The frequency must be configured with an integer number in MHz and
           must be according to ranges.";
    }

    revision "2021-05-07" {
        description
          "First release: add a type deviation for frequency";
    }

    deviation /oc-platf:components/oc-platf:component/oc-opt-term:optical-channel/oc-opt-term:config/oc-opt-term:frequency {
        deviate replace {
            type uint64 {
                range "191300000..196102997";
            }
        }
    }

    deviation /oc-opt-term:terminal-device/oc-opt-term:logical-channels/oc-opt-term:channel/oc-opt-term:otn/oc-opt-term:state/oc-opt-term:pre-fec-ber/oc-opt-term:instant {
        deviate replace {
            type uint64;
        }
    }

    deviation /oc-opt-term:terminal-device/oc-opt-term:logical-channels/oc-opt-term:channel/oc-opt-term:otn/oc-opt-term:state/oc-opt-term:post-fec-ber/oc-opt-term:instant {
        deviate replace {
            type uint64;
        }
    }
}

/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-lacp.yang
*
*/

module ipi-lacp {

    yang-version 1.1;

    namespace   "http://www.ipinfusion.com/yang/ocnos/ipi-lacp";

    prefix "ipi-lacp";

    import cml-data-types {
        prefix cml-data-types;
        revision-date 2022-04-04;
    }

    import ipi-lag-types {
        prefix ipi-lag-types;
        revision-date 2021-09-03;
    }

    import ietf-yang-types {
        prefix yang;
        revision-date 2013-07-15;
    }

    import ipi-interface {
        prefix ipi-interface;
        revision-date 2022-04-05;
    }

    import ipi-if-aggregate {
        prefix ipi-if-aggregate;
        revision-date 2022-04-20;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for Layer-2 LACP";


    revision "2020-12-15" {
        description "Change to have data-types in lower case instead of camel case";
        reference " 0.2.0.";
    }

    revision "2018-06-21" {
        description "Initial Version";
        reference " 0.1.0.";
    }



    typedef  lacp_activity_type_t {
        type enumeration {
            enum passive {
                value 0;
                description "Set LACP membership type is passive";
            }
            enum active {
                value 1;
                description "Set LACP membership type is active";
            }
        }
        description "type definition for LACP_ACTIVITY_TYPE_T";
    }

    typedef  lacp_timeout_type_t {
        type enumeration {
            enum long {
                value 0;
                description "Set LACP long timeout";
            }
            enum short {
                value 1;
                description "Set LACP short timeout";
            }
        }
        description "type definition for LACP_TIMEOUT_TYPE_T";
    }

    typedef  lacp_synchronization_type_t {
        type enumeration {
            enum out-of-sync {
                value 0;
                description "LACP synchronization is out of sync";
            }
            enum in-sync {
                value 1;
                description "LACP synchronization is in sync";
            }
        }
        description "type definition for LACP_SYNCHRONIZATION_TYPE_T";
    }

    typedef  lacp_bridgetype_t {
        type enumeration {
            enum customer-bridge-group-address {
                value 0;
                description "customer bridge group address";
            }
            enum multicast-group-address {
                value 1;
                description "multicast group address";
            }
            enum non-tmpr-group-address {
                value 2;
                description "non TPMR group address";
            }
        }
        description "type definition for LACP_BRIDGETYPE_T";
    }

    typedef  lacp_debug_type_t {
        type bits {
            bit event {
                position 0;
                description "Set the debug options for LACP events";
            }
            bit cli {
                position 1;
                description "Echo commands to console";
            }
            bit timer {
                position 2;
                description "Echo timer expiry to console";
            }
            bit packet {
                position 3;
                description "Set the debug option for LACP packet";
            }
            bit rx {
                position 4;
                description "Echo receiving of LACP PDUs to console";
            }
            bit tx {
                position 5;
                description "Echo transmission of LACP PDUs to console";
            }
            bit sync {
                position 6;
                description "Echo synchronization to console";
            }
            bit ha {
                position 7;
                description "Echo High availability events to console";
            }
        }
        description "type definition for LACP_DEBUG_TYPE_T";
    }

    typedef  lacp_rcv_state_t {
        type enumeration {
            enum Invalid {
                value 0;
                description "LACP Receive machine state is Invalid";
            }
            enum Initialize {
                value 1;
                description "LACP Receive machine state is Initialize";
            }
            enum Port-disabled {
                value 2;
                description "LACP Receive machine state is Port disabled";
            }
            enum LACP-disabled {
                value 3;
                description "LACP Receive machine state is LACP disabled";
            }
            enum Expired {
                value 4;
                description "LACP Receive machine state is Expired";
            }
            enum Defaulted {
                value 5;
                description "LACP Receive machine state is Defaulted";
            }
            enum Current {
                value 6;
                description "LACP Receive machine state is Current";
            }
        }
        description "type definition for LACP_RCV_STATE_T";
    }

    typedef  lacp_periodic_tx_state_t {
        type enumeration {
            enum Invalid {
                value 0;
                description "LACP Periodic Transmission machine state is Invalid";
            }
            enum No-periodic {
                value 1;
                description "LACP Periodic Transmission machine state is No periodic";
            }
            enum Fast-periodic {
                value 2;
                description "LACP Periodic Transmission machine state is Fast periodic";
            }
            enum Slow-periodic {
                value 3;
                description "LACP Periodic Transmission machine state is Slow periodic";
            }
            enum Periodic {
                value 4;
                description "LACP Periodic Transmission machine state is Periodic";
            }
        }
        description "type definition for LACP_PERIODIC_TX_STATE_T";
    }

    typedef  lacp_mux_state_t {
        type enumeration {
            enum Detached {
                value 0;
                description "LACP Mux machine state is Detached";
            }
            enum Waiting {
                value 1;
                description "LACP Mux machine state is Waiting";
            }
            enum Attached {
                value 2;
                description "LACP Mux machine state is Attached";
            }
            enum Collecting {
                value 3;
                description "LACP Mux machine state is Collecting";
            }
            enum Distributing {
                value 4;
                description "LACP Mux machine state is Distributing";
            }
            enum Collecting-Distributing {
                value 5;
                description "LACP Mux machine state is Collecting Distributing";
            }
        }
        description "type definition for LACP_MUX_STATE_T";
    }

    typedef  lacp_individual_aggregator_t {
        type enumeration {
            enum aggregator {
                value 0;
                description "Aggregator represents an Aggregate";
            }
            enum individual {
                value 1;
                description "Aggregator represents an Individual link";
            }
        }
        description "type definition for LACP_INDIVIDUAL_AGGREGATOR_T";
    }    grouping lacp-global-config {
        description
            "Global configuration data for LACP";
        leaf system-priority  {
            type  uint32 {
                 range "0..65535"  {
                    description "0..65535:LACP system priority 1-65535 default 32768";
                 }
            }
            default "32768";
            description "Use this attribute to the system priority of this switch. This
                        priority is used for determining the system that is responsible for
                        resolving conflicts in the choice of aggregation groups. A lower
                        numerical value has a higher priority.";
        } // END of system-priority definition.

    } // END of lacp-global-config definition.
    grouping lacp-debug-state {
        description
            "Global operational data for LACP";
        leaf debug-lacp  {
            type  lacp_debug_type_t;
            description "Use this command to turn on, and turn off, LACP debugging at various
                        levels.";
        } // END of debug-lacp definition.

    } // END of lacp-debug-state definition.
    grouping lacp-global-state {
        description
            "Global operational data for LACP";
        leaf system-id  {
            type  cml-data-types:cml_mac_addr_t {
                length "1..1965";
            }
            config false;
            description "Mac Address value that defines the system id for the system";
        } // END of system-id definition.

    } // END of lacp-global-state definition.
    grouping lacp-aggregator-state {
        description
            "LACP aggregator operational attributes";
        leaf agg-name  {
            type  string {
                length "1..1965";
                pattern "[^?' =,>|]+";
            }
            description "Aggregator name";
        } // END of agg-name definition.

        leaf interface-index  {
            type  uint32;
            description "Aggregator Interface index";
        } // END of interface-index definition.

        leaf type  {
            type  ipi-lag-types:lag_aggregator_type_t;
            description "Aggregator Interface Type";
        } // END of type definition.

        leaf mac-address  {
            type  cml-data-types:cml_mac_addr_t {
                length "1..1965";
            }
            description "Individual MAC address assigned to the Aggregator";
        } // END of mac-address definition.

        leaf rx-link-count  {
            type  yang:counter32;
            description "Number of links in the aggregator with MUX state supporting COLLECTING";
        } // END of rx-link-count definition.

        leaf tx-link-count  {
            type  yang:counter32;
            description "Number of links in the aggregator with MUX state supporting
                        DISTRIBUTING";
        } // END of tx-link-count definition.

        leaf individual-aggregator  {
            type  lacp_individual_aggregator_t;
            description "Indicates whether the Aggregator represents an Aggregate (0) or an
                        Individual link (1).";
        } // END of individual-aggregator definition.

        leaf aggregator-ready  {
            type  empty;
            description "Aggregator status on wait while timer expiry";
        } // END of aggregator-ready definition.

    } // END of lacp-aggregator-state definition.
    grouping lacp-aggregator-common-state {
        description
            "Actor, Partner operational attributes of LACP aggregator";
        leaf oper-key  {
            type  uint16;
            description "Current operational value of the key for the aggregate interface";
        } // END of oper-key definition.

        leaf system-priority  {
            type  uint16;
            description "Indicates the priority value associated with the System ID. Lower
                        value is higher priority";
        } // END of system-priority definition.

        leaf system-id  {
            type  cml-data-types:cml_mac_addr_t {
                length "1..1965";
            }
            description "MAC address that defines the system ID for the aggregate interface";
        } // END of system-id definition.

    } // END of lacp-aggregator-common-state definition.
    grouping lacp-aggregator-link-state {
        description
            "Operational attributes of LACP aggregated Links";
        leaf link-name  {
            type  string {
                length "1..1965";
                pattern "[^?' =,>|]+";
            }
            description "Name of LACP Aggregated Link";
        } // END of link-name definition.

        leaf sync-state  {
            type  lacp_synchronization_type_t;
            description "Indicates LACP synchronization state";
        } // END of sync-state definition.

        leaf receive-state  {
            type  lacp_rcv_state_t;
            description "Indicates the Receive state machine for the Aggregation Port";
        } // END of receive-state definition.

        leaf periodic-transmission-state  {
            type  lacp_periodic_tx_state_t;
            description "The period type of LACP PDU transmission";
        } // END of periodic-transmission-state definition.

        leaf mux-machine-state  {
            type  lacp_mux_state_t;
            description "This attribute indicates the Mux state machine for the Aggregation
                        Port";
        } // END of mux-machine-state definition.

        leaf protocol-destination-mac  {
            if-feature feature-list:HAVE_LACPV2;
            type  ipi-lag-types:lacp_protocol_dest_addr_type_t;
            description "Multicast destination address types for LACP PDUs";
        } // END of protocol-destination-mac definition.

        leaf admin-key  {
            type  uint16;
            description "Administrative value of the key for the aggregated link";
        } // END of admin-key definition.

        container counters {
            config false;
            description
                "Counters for LACP aggregated links";
            leaf lacp-out-pkts  {
                type  yang:counter32;
                description "Number of LACP PDUs transmitted";
            } // END of lacp-out-pkts definition.

            leaf lacp-in-pkts  {
                type  yang:counter32;
                description "Number of LACP PDUs received";
            } // END of lacp-in-pkts definition.

            leaf lacp-in-marker-pdu  {
                type  yang:counter32;
                description "The number of valid Marker PDUs received on this Aggregation Port";
            } // END of lacp-in-marker-pdu definition.

            leaf lacp-out-marker-pdu  {
                type  yang:counter32;
                description "The number of valid Marker PDUs transmitted on this Aggregation Port";
            } // END of lacp-out-marker-pdu definition.

            leaf lacp-tx-errors  {
                type  yang:counter32;
                description "Number of LACPDU transmit packet errors";
            } // END of lacp-tx-errors definition.

            leaf lacp-rx-errors  {
                type  yang:counter32;
                description "Number of LACPDU receive packet errors";
            } // END of lacp-rx-errors definition.

            leaf lacp-in-marker-pdu-response  {
                type  yang:counter32;
                description "The number of valid Marker Response PDUs received on this Aggregation
                            Port";
            } // END of lacp-in-marker-pdu-response definition.

            leaf lacp-out-marker-pdu-response  {
                type  yang:counter32;
                description "The number of valid Marker Response PDUs transmitted on this
                            Aggregation Port";
            } // END of lacp-out-marker-pdu-response definition.

        } // END of counters-container definition.
    } // END of lacp-aggregator-link-state definition.
    grouping lacp-aggregator-link-csfcd-state {
        description
            "Operational data related to Conversation Sensitive Frame Collection
                        and Distribution";
        leaf partner-conversation-mask-sync  {
            type  empty;
            description "Indicates that conversation mask sync received in the PDU from the
                        partner";
        } // END of partner-conversation-mask-sync definition.

        leaf local-conversation-mask-sync  {
            type  empty;
            description "Indicates whether the port conversation mask is in sync with the
                        partner converation mask received in the PDU";
        } // END of local-conversation-mask-sync definition.

        leaf long-lacp-pdu-transmit  {
            type  empty;
            description "Indicates whether Long LACP pdu is sent, when
                        partner-conversation-mask-sync and local-conversation-mask-sync are
                        false";
        } // END of long-lacp-pdu-transmit definition.

    } // END of lacp-aggregator-link-csfcd-state definition.
    grouping aggregator-link-state {
        description
            "Operational data for Aggregated link";
        leaf activity  {
            type  lacp_activity_type_t;
            config false;
            description "Describes the LACP membership type, active or passive, of the
                        interface in the aggregate";
        } // END of activity definition.

        leaf timeout  {
            type  lacp_timeout_type_t;
            config false;
            description "Type of timeout used, short or long, by LACP participants";
        } // END of timeout definition.

        leaf aggregatable  {
            type  boolean;
            config false;
            description "A true value indicates that the participant will allow the link to be
                        used as part of the aggregate. A false value indicates the link should
                        be used as an individual link";
        } // END of aggregatable definition.

        leaf synchronization  {
            type  lacp_synchronization_type_t;
            config false;
            description "Indicates whether the participant is in-sync or out-of-sync";
        } // END of synchronization definition.

        leaf collecting  {
            type  boolean;
            config false;
            description "If true, the participant is collecting incoming frames on the link,
                        otherwise false";
        } // END of collecting definition.

        leaf distributing  {
            type  boolean;
            config false;
            description "When true, the participant is distributing outgoing frames; when
                        false, distribution is disabled";
        } // END of distributing definition.

        leaf defaulted  {
            type  boolean;
            config false;
            description "Indicates whether the participant is in defaulted state - no LACP PDUs
                        are being received from the LACP partner device";
        } // END of defaulted definition.

        leaf expired  {
            type  boolean;
            config false;
            description "Indicates whether the participant is in expired state - no LACP PDUs
                        are being received from the LACP partner device in the current-while
                        period";
        } // END of expired definition.

    } // END of aggregator-link-state definition.
    grouping aggregator-key-info {
        description
            "Actor/Partner Port key";
        leaf port-key  {
            type  uint16;
            description "Configured value of the key for the aggregate interface";
        } // END of port-key definition.

    } // END of aggregator-key-info definition.
    grouping lacp-aggregator-link-common-state {
        description
            "Actor/Partner Admin/Oper data for Aggregated link";
        leaf system-id  {
            type  cml-data-types:cml_mac_addr_t {
                length "1..1965";
            }
            description "MAC address that defines the system ID for the aggregate interface";
        } // END of system-id definition.

        leaf system-priority  {
            type  uint16;
            description "Indicates the priority value associated with the System ID";
        } // END of system-priority definition.

        leaf port-number  {
            type  uint16;
            description "Port number of the aggregation member";
        } // END of port-number definition.

        leaf port-priority  {
            type  uint16;
            description "The priority value assigned to this Aggregation Port";
        } // END of port-priority definition.

    } // END of lacp-aggregator-link-common-state definition.
    grouping lacp-admin-key-grouping {
        description
            "Grouping for Admin key information";
        leaf admin-key  {
            type  uint16;
            description "Administrative value of the key for the aggregated link";
        } // END of admin-key definition.

    } // END of lacp-admin-key-grouping definition.
    grouping lacp-aggregator-members {
        description
            "Grouping for LACP aggregator members";
        container members {
            config false;
            description
                "Links of LACP aggregator";

            list member {
                key "link-name";
                config false;
                description
                    "List of links in lacp aggregator";
                leaf link-name  {
                    type  leafref {
                        path  "../state/link-name";
                    }
                    description "LACP Aggregated Link Name";
                } // END of link-name definition.

                container state {
                    config false;
                    description
                        "Operational data for links in LACP aggregator";
                    uses lacp-aggregator-link-state;
                } // END of state-container definition.
                container conversation-sensitive-frame-distribution {
                    if-feature feature-list:HAVE_LACPV2;
                    config false;
                    description
                        "Conversation Sensitive Frame Collection and Distribution";
                    container state {
                        if-feature feature-list:HAVE_LACPV2;
                        config false;
                        description
                            "Operational data related to Conversation Sensitive Frame Collection
                                    and Distribution";
                        uses lacp-aggregator-link-csfcd-state;
                    } // END of state-container definition.
                } // END of conversation-sensitive-frame-distribution-container definition.
                container actor {
                    config false;
                    description
                        "Actor specific data for LACP aggregated links";
                    container state {
                        config false;
                        description
                            "Actor specific admin/oper data for LACP aggregated links";
                        leaf version  {
                            if-feature feature-list:HAVE_LACPV2;
                            type  ipi-lag-types:lacp_version_t;
                            description "LACP version number";
                        } // END of version definition.

                        container operational {
                            config false;
                            description
                                "Actor operational data for LACP aggregated links";
                            uses aggregator-link-state;
                            uses aggregator-key-info;
                        } // END of operational-container definition.
                        container admin {
                            config false;
                            description
                                "Actor admin data for LACP aggregated links";
                            uses aggregator-link-state;
                            uses aggregator-key-info;
                        } // END of admin-container definition.
                        uses lacp-aggregator-link-common-state;
                    } // END of state-container definition.
                } // END of actor-container definition.
                container partner {
                    config false;
                    description
                        "Partner specific data for LACP aggregators";
                    container state {
                        config false;
                        description
                            "Partner specific admin/operational data for LACP aggregators";
                        leaf lacp-pdu-version  {
                            if-feature feature-list:HAVE_LACPV2;
                            type  ipi-lag-types:lacp_version_t;
                            description "LACP PDU version number";
                        } // END of lacp-pdu-version definition.

                        container operational {
                            config false;
                            description
                                "Partner operational data for LACP aggregated links";
                            uses aggregator-link-state;
                            uses lacp-aggregator-link-common-state;
                            uses aggregator-key-info;
                        } // END of operational-container definition.
                        container admin {
                            config false;
                            description
                                "Partner admin data for LACP aggregated links";
                            uses aggregator-link-state;
                            uses lacp-aggregator-link-common-state;
                        } // END of admin-container definition.
                    } // END of state-container definition.
                } // END of partner-container definition.
            } // End of member-list
        } // END of members-container definition.
    } // END of lacp-aggregator-members definition.
    grouping lacp-aggregators {
        description
            "LACP aggregator runtime attributes";
        container aggregators {
            config false;
            description
                "LACP aggregators";

            list aggregator {
                key "agg-name";
                config false;
                description
                    "List of lacp aggregators";
                leaf agg-name  {
                    type  leafref {
                        path  "../state/agg-name";
                    }
                    description "Aggregator Name";
                } // END of agg-name definition.

                container state {
                    config false;
                    description
                        "Operational data for LACP aggregators";
                    uses lacp-aggregator-state;
                } // END of state-container definition.
                container actor {
                    config false;
                    description
                        "Actor specific data for LACP aggregators";
                    container state {
                        config false;
                        description
                            "Actor specific operational data for LACP aggregators";
                        uses lacp-admin-key-grouping;
                        uses lacp-aggregator-common-state;
                    } // END of state-container definition.
                } // END of actor-container definition.
                container partner {
                    config false;
                    description
                        "Partner specific data for LACP aggregators";
                    container state {
                        config false;
                        description
                            "Partner specific operational data for LACP aggregators";
                        uses lacp-aggregator-common-state;
                    } // END of state-container definition.
                } // END of partner-container definition.
                uses lacp-aggregator-members;
            } // End of aggregator-list
        } // END of aggregators-container definition.
    } // END of lacp-aggregators definition.
    grouping lacp-interface-aggregated-config {
        description
            "LACP aggregated interface related attributes";
        leaf port-priority  {
            type  uint32 {
                 range "1..65535"  {
                    description "1..65535:LACP port priority";
                 }
            }
            default "32768";
            description "Use this attribute to set the priority of a channel. Channels are
                        selected for aggregation based on their priority with the higher
                        priority (numerically lower) channels selected first";
        } // END of port-priority definition.

        leaf timeout  {
            type  lacp_timeout_type_t;
            default "long";
            description "Use this attribute to set either a short or long timeout value on a
                        port. The timeout value is the number of seconds before invalidating a
                        received LACP data unit (DU). If the LACP_timeout bit (encoded in
                        Actor_State and Partner_State fields) is set to 1, the short timeout
                        takes effect; if set to 0, the long timeout takes effect.";
        } // END of timeout definition.

        leaf bridge-type  {
            type  lacp_bridgetype_t;
            default "multicast-group-address";
            description "Use this attribute to set the address type to use for sending LACPDUs
                        (Link Aggregation Control Protocol Data Units).";
        } // END of bridge-type definition.

        leaf force-up  {
            when " /ipi-interface:interfaces/ipi-interface:interface/ipi-if-aggregate:member-aggregation/ipi-if-aggregate:config/ipi-if-aggregate:lacp-mode = 'active' ";
            type  empty;
            description "Use this attribute to enable the port as force-up in a channel group.
                        Setting this attribute makes the port logically operational even if
                        link aggregation goes down.";
        } // END of force-up definition.

    } // END of lacp-interface-aggregated-config definition.
    grouping lacp-interface-aggregator-config {
        description
            "LACP aggregator interface related attributes";
        leaf discard-conversation  {
            if-feature feature-list:HAVE_LACPV2;
            type  ipi-lag-types:lacp_discard_conv_t;
            default "disable";
            description "Use this attribute to enable or disable discarding frames with an
                        incorrect port conversation identifier.";
        } // END of discard-conversation definition.

    } // END of lacp-interface-aggregator-config definition.
    grouping lacp-interfaces {
        description
            "LACP interface related attributes";
        container interfaces {
            description
                "LACP interface related Configurations";

            list interface {
            when " /ipi-interface:interfaces/ipi-interface:interface/ipi-if-aggregate:member-aggregation/ipi-if-aggregate:config + /ipi-interface:interfaces/ipi-interface:interface/ipi-if-aggregate:member-aggregation/ipi-if-aggregate:config/ipi-if-aggregate:agg-type = 'lacp' ";
                key "name";
                description
                    "LACP interface list";
                leaf name  {
                    type  leafref {
                        path  "/ipi-interface:interfaces/ipi-interface:interface/ipi-interface:name";
                    }
                    description "Reference to the base interface name";
                } // END of name definition.

                container member-aggregation {
                    description
                        "LACP aggregated interface related Configurations";
                    container config {
                        description
                            "LACP aggregated interface related Configurations";
                        uses lacp-interface-aggregated-config;
                    } // END of config-container definition.
                    container state {
                        config false;
                        description
                            "Operational date for LACP aggregated interface";
                        uses lacp-interface-aggregated-config;
                    } // END of state-container definition.
                } // END of member-aggregation-container definition.
                container aggregator {
                    description
                        "LACP aggregator interface related Configurations";
                    container config {
                        description
                            "LACP aggregator interface related Configurations";
                        uses lacp-interface-aggregator-config;
                    } // END of config-container definition.
                    container state {
                        config false;
                        description
                            "Operational date for LACP aggregator interface";
                        uses lacp-interface-aggregator-config;
                    } // END of state-container definition.
                } // END of aggregator-container definition.
            } // End of interface-list
        } // END of interfaces-container definition.
    } // END of lacp-interfaces definition.

    grouping  lacp-grouping {
    description
        "Top level container for LACP";
    container lacp {
        description
            "Top level container for LACP";
        container global {
            description
                "Global container for LACP";
            container config {
                description
                    "Configurable attributes at the global level";
                uses lacp-global-config;
            } // END of config-container definition.
            container state {
                config false;
                description
                    "Operational data at the global interface level";
                uses lacp-global-config;
                uses lacp-global-state;
            } // END of state-container definition.
        } // END of global-container definition.
        container debug {
            description
                "Global container for LACP";
            container state {
                config false;
                description
                    "Operational attributes for the LACP debug";
                uses lacp-debug-state;
            } // END of state-container definition.
        } // END of debug-container definition.
        uses lacp-aggregators;
        uses lacp-interfaces;
    } // END of lacp-container definition.
    } // END of lacp-grouping definition.

    uses lacp-grouping;

    rpc lacp-snmp-restart {
        description "Use this RPC to restart SNMP in LAG/LACP";
    }

    rpc clear-lacp-counters {
        description "Use this RPC to clear the LACP counters";
        input  {
            leaf aggregate-id  {
                type uint16 {
                    range "1..65535";
                }
                mandatory true;
                description "Use this attribute to specify the Channel-group number";
            }
        }
    }

    rpc lacp-debug-on {
        description "Use this RPC to enable the LAG/LACP debugging logs";
        input  {
            leaf debug-options  {
                type lacp_debug_type_t;
                mandatory true;
                description "Use this command to turn on, and turn off, LACP debugging at various
                            levels.";
            }
        }
    }

    rpc lacp-debug-off {
        description "Use this RPC to disable the LAG/LACP debugging logs";
        input  {
            leaf debug-options  {
                type lacp_debug_type_t;
                mandatory true;
                description "Use this command to turn on, and turn off, LACP debugging at various
                            levels.";
            }
        }
    }

}

/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-lag-types.yang
*
*/

module ipi-lag-types {

    yang-version 1.1;

    namespace   "http://www.ipinfusion.com/yang/ocnos/ipi-lag-types";

    prefix "ipi-lag-types";

    organization
        "IP Infusion Inc.";

    contact
        "Address: 3965 Freedom Circle, Suite 200, Santa Clara, CA 95054
         Phone: +1 408-400-1900
         E-mail: support@ipinfusion.com
         Web: http://www.ipinfusion.com/";

    description
        "Generic Network Instance";


    revision "2021-09-03" {
        description "Update descriptions of attribute";
        reference " 0.3.0.";
    }

    revision "2020-12-15" {
        description "Change to have data-types in lower case instead of camel case";
        reference " 0.2.0.";
    }

    revision "2018-06-21" {
        description "Initial Version";
        reference " 0.1.0.";
    }



    typedef  lag_aggregator_type_t {
        type enumeration {
            enum Layer3 {
                value 0;
                description "Layer3 aggregator";
            }
            enum Layer2 {
                value 1;
                description "Layer2 aggregator";
            }
        }
        description "type definition for LAG_AGGREGATOR_TYPE_T";
    }

    typedef  lacp_protocol_dest_addr_type_t {
        type enumeration {
            enum 01-80-c2-00-00-00 {
                value 0;
                description "LACP_NR_CUST_BR_ADDR";
            }
            enum 01-80-c2-00-00-02 {
                value 1;
                description "LACP_MCAST_GRP_ADDR";
            }
            enum 01-80-c2-00-00-03 {
                value 2;
                description "LACP_NR_NON_TPMR_BR_ADDR";
            }
        }
        description "type definition for LACP_PROTOCOL_DEST_ADDR_TYPE_T";
    }

    typedef  lacp_discard_conv_t {
        type enumeration {
            enum disable {
                value 0;
                description "disable";
            }
            enum enable {
                value 1;
                description "enable";
            }
        }
        description "type definition for LACP_DISCARD_CONV_T";
    }

    typedef  lag_link_agg_type_t {
        type enumeration {
            enum lacp {
                value 1;
                description "Set LACP link aggregation type is lacp";
            }
            enum static {
                value 2;
                description "Set LACP link aggregation type is static";
            }
        }
        description "type definition for LAG_LINK_AGG_TYPE_T";
    }

    typedef  lacp_mode_t {
        type enumeration {
            enum passive {
                value 0;
                description "Disable initiation of LACP negotiation on a port";
            }
            enum active {
                value 1;
                description "Enable initiation of LACP negotiation on a port";
            }
        }
        description "type definition for LACP_MODE_T";
    }

    typedef  lag_load_balancing_criteria_t {
        type enumeration {
            enum dst-mac {
                value 1;
                description "Destination Mac address based load balancing";
            }
            enum src-mac {
                value 2;
                description "Source Mac address based load balancing";
            }
            enum src-dst-mac {
                value 3;
                description "Source and Destination Mac address based load balancing";
            }
            enum src-ip {
                value 4;
                description "Source IP address based load balancing";
            }
            enum dst-ip {
                value 5;
                description "Destination IP address based load balancing";
            }
            enum src-dst-ip {
                value 6;
                description "Source and Destination IP address based load balancing";
            }
            enum src-port {
                value 7;
                description "Source TCP/UDP port based load balancing";
            }
            enum dst-port {
                value 8;
                description "Destination TCP/UDP port based load balancing";
            }
            enum src-dst-port {
                value 9;
                description "Source and Destination TCP/UDP port based load balancing";
            }
        }
        description "type definition for LAG_LOAD_BALANCING_CRITERIA_T";
    }

    typedef  lag_agg_min_links_status {
        type enumeration {
            enum up {
                value 1;
                description "min link aggregation status is up";
            }
            enum down {
                value 2;
                description "min link aggregation status is down";
            }
        }
        description "type definition for LAG_AGG_MIN_LINKS_STATUS";
    }

    typedef  lacp_version_t {
        type enumeration {
            enum lacpv1 {
                value 1;
                description "LACP version number of LACPV1 (1)";
            }
            enum lacpv2 {
                value 2;
                description "LACP version number of LACPV2 (2)";
            }
        }
        description "type definition for LACP_VERSION_T";
    }

}

/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-mpls-types.yang
*
*/

module ipi-mpls-types {

    yang-version 1.1;

    namespace   "http://www.ipinfusion.com/yang/ocnos/ipi-mpls-types";

    prefix "ipi-mpls-types";

    organization
        "IP Infusion Inc.";

    contact
        "Address: 3965 Freedom Circle, Suite 200, Santa Clara, CA 95054
         Phone: +1 408-400-1900
         E-mail: support@ipinfusion.com
         Web: http://www.ipinfusion.com/";

    description
        "MPLS data types";


    revision "2022-02-15" {
        description "Added datatype MPLS_DSTE_BC_MODE_T";
        reference " 0.5.1.";
    }

    revision "2022-01-24" {
        description "Added backup nhlfe support for FTN Entries";
        reference " 0.5.0.";
    }

    revision "2021-09-03" {
        description "Update descriptions of attribute";
        reference " 0.4.2.";
    }

    revision "2021-08-17" {
        description "Added data-type for operational state of RSVP and LDP Graceful-restart";
        reference " 0.4.1.";
    }

    revision "2021-02-12" {
        description "Netconf datamodel restructuring for Static ILM/FTN";
        reference " 0.4.0.";
    }

    revision "2021-01-27" {
        description "Change for restructuring Label Management and admin group CLIs";
        reference " 0.3.0.";
    }

    revision "2020-12-15" {
        description "Change to have data-types in lower case instead of camel case";
        reference " 0.2.0.";
    }

    revision "2020-11-03" {
        description "Initial Version";
        reference " 0.1.0.";
    }



    typedef  mpls_rib_entry_owner_t {
        type enumeration {
            enum unknown {
                value 1;
                description "Unknown";
            }
            enum other {
                value 2;
                description "Other";
            }
            enum snmp {
                value 3;
                description "SNMP";
            }
            enum ldp {
                value 4;
                description "LDP";
            }
            enum crldp {
                value 5;
                description "CRLDP";
            }
            enum rsvp {
                value 6;
                description "RSVP";
            }
            enum policy-agent {
                value 7;
                description "Policy Agent";
            }
            enum bgp {
                value 8;
                description "BGP";
            }
            enum cli {
                value 9;
                description "CLI";
            }
            enum ldp-vc {
                value 10;
                description "LDP VC";
            }
            enum igp-shortcut {
                value 12;
                description "IGP-Shortcut";
            }
            enum ospf-sr {
                value 13;
                description "OSPF-SR";
            }
            enum ospf6-sr {
                value 14;
                description "OSPF6-SR";
            }
            enum isis-sr {
                value 15;
                description "ISIS-SR";
            }
            enum rsvp-ecmp {
                value 16;
                description "RSVP-ECMP";
            }
            enum cli-sr {
                value 17;
                description "CLI-SR";
            }
            enum sr-policy {
                value 18;
                description "SR-POLICY";
            }
            enum not-applicable {
                value 19;
                description "N/A";
            }
        }
        description "type definition for MPLS_RIB_ENTRY_OWNER_T";
    }

    typedef  mpls_rib_action_type_t {
        type enumeration {
            enum drop {
                value 1;
                description "Drop";
            }
            enum redirect-lsp {
                value 2;
                description "Redirect to LSP";
            }
            enum redirect-tunnel {
                value 3;
                description "Redirect to Tunnel";
            }
        }
        description "type definition for MPLS_RIB_ACTION_TYPE_T";
    }

    typedef  mpls_rib_label_op_code_t {
        type enumeration {
            enum push {
                value 1;
                description "Push";
            }
            enum pop {
                value 2;
                description "Pop";
            }
            enum swap {
                value 3;
                description "Swap";
            }
            enum pop-for-vpn {
                value 4;
                description "Pop for VPN";
            }
            enum deliver-to-ip {
                value 5;
                description "Deliver to IP";
            }
            enum push-and-lookup {
                value 6;
                description "Push and Lookup";
            }
            enum push-for-vc {
                value 7;
                description "Push for VC";
            }
            enum push-and-look-up-for-vc {
                value 8;
                description "Push and Lookup for VC";
            }
            enum pop-for-vc {
                value 9;
                description "Pop for VC";
            }
            enum swap-and-lookup {
                value 10;
                description "Swap and Lookup";
            }
            enum continue {
                value 11;
                description "Continue";
            }
        }
        description "type definition for MPLS_RIB_LABEL_OP_CODE_T";
    }

    typedef  mpls_rib_entry_admin_status_t {
        type enumeration {
            enum up {
                value 1;
                description "Up";
            }
            enum down {
                value 2;
                description "Down";
            }
            enum testing {
                value 3;
                description "Testing";
            }
        }
        description "type definition for MPLS_RIB_ENTRY_ADMIN_STATUS_T";
    }

    typedef  mpls_rib_entry_oper_status_t {
        type enumeration {
            enum up {
                value 1;
                description "Up";
            }
            enum down {
                value 2;
                description "Down";
            }
            enum testing {
                value 3;
                description "Testing";
            }
            enum unknown {
                value 4;
                description "Unknown";
            }
            enum dormant {
                value 5;
                description "Dormant";
            }
            enum not-present {
                value 6;
                description "Not present";
            }
            enum link-layer-down {
                value 7;
                description "Link Layer Down";
            }
        }
        description "type definition for MPLS_RIB_ENTRY_OPER_STATUS_T";
    }

    typedef  mpls_rib_lsp_type_t {
        type enumeration {
            enum primary {
                value 1;
                description "Primary LSP";
            }
            enum secondary {
                value 2;
                description "Secondary LSP";
            }
            enum backup {
                value 3;
                description "Backup LSP";
            }
            enum bypass {
                value 4;
                description "Bypass LSP";
            }
        }
        description "type definition for MPLS_RIB_LSP_TYPE_T";
    }

    typedef  mpls_module_t {
        type enumeration {
            enum rsvp {
                value 0;
                description "Specify label range value for rsvp";
            }
            enum ldp {
                value 1;
                description "Specify label range value for ldp";
            }
            enum bgp {
                value 4;
                description "Specify label range value for bgp";
            }
        }
        description "type definition for MPLS_MODULE_T";
    }

    typedef  mpls_svc_tpid_t {
        type enumeration {
            enum dot1.q {
                value 33024;
                description "Set tpid value as 0x8100";
            }
            enum dot1.ad {
                value 34984;
                description "Set tpid value as 0x88a8";
            }
            enum 0x9100 {
                value 37120;
                description "Set tpid value as 0x9100";
            }
        }
        description "type definition for MPLS_SVC_TPID_T";
    }

    typedef  mpls_l2vpn_vlan_action_type_t {
        type enumeration {
            enum pop {
                value 1;
                description "Pop the outer vid";
            }
            enum push {
                value 2;
                description "Push the outer vid";
            }
            enum translate {
                value 3;
                description "Translate the outer vid";
            }
        }
        description "type definition for MPLS_L2VPN_VLAN_ACTION_TYPE_T";
    }

    typedef  mpls_l2vpn_serv_temp_error_status_t {
        type enumeration {
            enum Bind-Success {
                value 0;
                description "SVC binding succesful";
            }
            enum Bind-Failure {
                value 1;
                description "SVC binding Failure";
            }
            enum Config-Error {
                value 2;
                description "SVC binding Config Error";
            }
        }
        description "type definition for MPLS_L2VPN_SERV_TEMP_ERROR_STATUS_T";
    }

    typedef  mpls_vpls_ftn_entry_lsp_type_t {
        type enumeration {
            enum secondary {
                value 0;
                description "Secondary LSP";
            }
            enum primary {
                value 1;
                description "Primary LSP (default)";
            }
        }
        description "type definition for MPLS_VPLS_FTN_ENTRY_LSP_TYPE_T";
    }

    typedef  mpls_graceful_restart_status_t {
        type enumeration {
            enum inactive {
                value 0;
                description "LDP/RSVP is not in GR state";
            }
            enum active {
                value 1;
                description "LDP/RSVP is in GR state";
            }
        }
        description "type definition for MPLS_GRACEFUL_RESTART_STATUS_T";
    }

    typedef  mpls_tunnel_selection_mode_t {
        type enumeration {
            enum dedicated {
                value 1;
                description "Dedicated tunnel selection mode(Default)";
            }
            enum best-effort {
                value 2;
                description "Best effort tunnel selection mode";
            }
        }
        description "type definition for MPLS_TUNNEL_SELECTION_MODE_T";
    }

    typedef  mpls_rib_nhlfe_type_t {
        type enumeration {
            enum primary {
                value 0;
                description "Primary Next Hop";
            }
            enum backup {
                value 1;
                description "Backup Next Hop";
            }
        }
        description "type definition for MPLS_RIB_NHLFE_TYPE_T";
    }

    typedef  mpls_dste_bc_mode_t {
        type enumeration {
            enum mam {
                value 0;
                description "Bandwidth constraint mode MAM";
            }
            enum rsdl {
                value 1;
                description "Bandwidth constraint mode RSDL";
            }
            enum mar {
                value 2;
                description "Bandwidth constraint mode MAR";
            }
        }
        description "type definition for MPLS_DSTE_BC_MODE_T";
    }

}

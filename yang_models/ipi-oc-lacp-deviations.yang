module ipi-oc-lacp-deviations {
  namespace   "http://www.ipinfusion.com/yang/ocnos/ipi-oc-lacp-deviations";
  prefix "ipi-oc-lacp-deviations";

  import openconfig-lacp { prefix oc-lacp; }

  revision "2021-03-01" {
    description
      "First release: add restrictions to LAG interface mode";
    reference "2.4.3";
  }

  deviation /oc-lacp:lacp/oc-lacp:interfaces/oc-lacp:interface/oc-lacp:config/oc-lacp:lacp-mode {
    deviate not-supported;
  }
}

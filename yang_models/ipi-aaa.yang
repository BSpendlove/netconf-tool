/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-aaa.yang
*
*/

module ipi-aaa {

    yang-version 1.1;

    namespace   "http://www.ipinfusion.com/yang/ocnos/ipi-aaa";

    prefix "ipi-aaa";

    import cml-data-types {
        prefix cml-data-types;
        revision-date 2022-04-04;
    }

    import ipi-aaa-types {
        prefix ipi-aaa-types;
        revision-date 2021-09-03;
    }

    import ipi-vrf {
        prefix ipi-vrf;
        revision-date 2021-09-03;
    }

    import ipi-network-instance {
        prefix ipi-network-instance;
        revision-date 2021-11-10;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 aaa configurations";


    revision "2021-12-02" {
        description "Remodeled AAA Group Server list and added dependency constraints";
        reference " 0.3.0.";
    }

    revision "2021-09-21" {
        description "Updated length validation to AAA Group Name attribute";
        reference " 0.2.3.";
    }

    revision "2021-09-03" {
        description "Update descriptions of attribute";
        reference " 0.2.2.";
    }

    revision "2021-08-30" {
        description "Added RPC to unlock the user that is locked";
        reference " 0.2.1.";
    }

    revision "2021-07-16" {
        description "Restructured module as per open-config style";
        reference " 0.2.0.";
    }

    revision "2018-06-21" {
        description "Initial Version";
        reference " 0.1.0.";
    }

    grouping aaa-method-config {
        description
            "Configuration data for AAA method rules";
        leaf vrf-name  {
            type  leafref {
                path  "/ipi-network-instance:network-instances/ipi-network-instance:network-instance/ipi-vrf:vrf/ipi-vrf:config/ipi-vrf:vrf-name";
            }
            description "VRF Name associated with this instance";
        } // END of vrf-name definition.

        leaf authentication-method-rule  {
            type  cml-data-types:cml_line_t {
                length "1..1965";
            }
            description "Use this attribute to set AAA methods for authentication";
        } // END of authentication-method-rule definition.

        leaf accounting-method-rule  {
            type  cml-data-types:cml_line_t {
                length "1..1965";
            }
            description "Use this attribute to set AAA methods for accounting";
        } // END of accounting-method-rule definition.

        leaf enable-fallback  {
            type  empty;
            description "This is to enable fallback to local authentication if remote
                        authentication is configured and all AAA servers are unreachable";
        } // END of enable-fallback definition.

        leaf error-enable  {
            type  empty;
            description "This is to enable error message on login failures";
        } // END of error-enable definition.

    } // END of aaa-method-config definition.
    grouping aaa-group-config {
        description
            "Configuration data for AAA server groups";
        leaf group-type  {
            type  ipi-aaa-types:aaa_server_grp_type_t;
            description "This is use to specify server type either tacacs+ or radius";
        } // END of group-type definition.

        leaf group-name  {
            type  string {
                length "1..127";
                pattern "[^?' =,>|]+";
            }
            description "This is to create server group name";
        } // END of group-name definition.

    } // END of aaa-group-config definition.
    grouping aaa-host-entry-config {
        description
            "AAA host address config";
        leaf host-address  {
            type  cml-data-types:cml_hostname_t;
            description "Use this attribute to add a host address to a server group";
        } // END of host-address definition.

    } // END of aaa-host-entry-config definition.
    grouping aaa-server-entries-top {
        description
            "Grouping of AAA Server Configuration";
        container server-addresses {
            description
                "Container for AAA Server address Entries";

            list server-address {
            // when " ipi-tacacs:tacacs/vrf/remote-servers/server/config/host-address || ipi-radius:radius/vrfs/vrf/remote-servers/server/config/host-address ";
                key "host-address";
                description
                    "AAA server address entry list";
                leaf host-address  {
                    type  leafref {
                        path  "../config/host-address";
                    }
                    description "Use this attribute to add a host address to a server group";
                } // END of host-address definition.

                container config {
                    description
                        "Configurational data for server address entry";
                    uses aaa-host-entry-config;
                } // END of config-container definition.
                container state {
                    config false;
                    description
                        "Operational state data for server address entry";
                    uses aaa-host-entry-config;
                } // END of state-container definition.
            } // End of server-address-list
        } // END of server-addresses-container definition.
    } // END of aaa-server-entries-top definition.
    grouping aaa-user-config {
        description
            "Configuration data for AAA user authentication";
        leaf authentication-max-failure-attempts  {
            type  uint8 {
                 range "1..25"  {
                    description "1..25:number of unsuccessful attempts";
                 }
            }
            description "Use this attribute to set the number of unsuccessful authentication
                        attempts before a user is locked out";
        } // END of authentication-max-failure-attempts definition.

        leaf local-user-unlock-timeout  {
            type  uint16 {
                 range "1..3600"  {
                    description "1..3600:Timeout value to unlock local user-acoounts in seconds
                            (default : 1200)";
                 }
            }
            units "seconds";
            description "Use this attribute to set unlock timeout after local user/s locked out";
        } // END of local-user-unlock-timeout definition.

    } // END of aaa-user-config definition.
    grouping aaa-debug-config {
        description
            "Configuration data for AAA debugging in Config Mode";
        leaf enable-debugging  {
            type  empty;
            description "Use this attribute to display AAA debugging information.";
        } // END of enable-debugging definition.

    } // END of aaa-debug-config definition.
    grouping aaa-debug-state {
        description
            "State data related to AAA debugging status";
        leaf terminal-debug-status  {
            type  cml-data-types:cml_on_off_t;
            description "Use this attribute to display AAA terminal debugging information.";
        } // END of terminal-debug-status definition.

    } // END of aaa-debug-state definition.

    grouping  aaa-grouping {
    description
        "AAA Top level container for configuration and operational data";
    container aaa {
        description
            "AAA Top level container for configuration and operational data";
        container vrfs {
            description
                "This container defines AAA server vrf informations";

            list vrf {
                key "vrf-name";
                description
                    "AAA VRF Configuration";
                leaf vrf-name  {
                    type  leafref {
                        path  "../config/vrf-name";
                    }
                    description "VRF Name associated with this instance";
                } // END of vrf-name definition.

                container config {
                    description
                        "AAA VRF related operation";
                    uses aaa-method-config;
                } // END of config-container definition.
                container state {
                    config false;
                    description
                        "This container defines AAA VRF states.";
                    uses aaa-method-config;
                } // END of state-container definition.
                container server-groups {
                    description
                        "This container defines AAA server groups informations";

                    list server-group {
                        key "group-type group-name";
                        description
                            "This objectlist defines AAA server group list";
                        leaf group-type  {
                            type  leafref {
                                path  "../config/group-type";
                            }
                            description "This is to create server group type";
                        } // END of group-type definition.

                        leaf group-name  {
                            type  leafref {
                                path  "../config/group-name";
                            }
                            description "This is to create server group name";
                        } // END of group-name definition.

                        container config {
                            description
                                "configuration data for each server group";
                            uses aaa-group-config;
                        } // END of config-container definition.
                        container state {
                            config false;
                            description
                                "Operational state data of each server group";
                            uses aaa-group-config;
                        } // END of state-container definition.
                        uses aaa-server-entries-top;
                    } // End of server-group-list
                } // END of server-groups-container definition.
            } // End of vrf-list
        } // END of vrfs-container definition.
        container aaa-user {
            description
                "This container defines a global admin data for AAA users";
            container config {
                description
                    "Configuration data for AAA users";
                uses aaa-user-config;
            } // END of config-container definition.
            container state {
                config false;
                description
                    "Operational state data for AAA users";
                uses aaa-user-config;
            } // END of state-container definition.
        } // END of aaa-user-container definition.
        container debug {
            description
                "This container defines AAA debuging Information";
            container config {
                description
                    "This defines AAA Debug Configuration";
                uses aaa-debug-config;
            } // END of config-container definition.
            container state {
                config false;
                description
                    "This container defines AAA Debug state";
                uses aaa-debug-config;
                uses aaa-debug-state;
            } // END of state-container definition.
        } // END of debug-container definition.
    } // END of aaa-container definition.
    } // END of aaa-grouping definition.

    uses aaa-grouping;

    rpc aaa-terminal-debugging-on {
        description "Use this RPC to turn on AAA terminal debug logs";
    }

    rpc aaa-terminal-debugging-off {
        description "Use this RPC to turn off AAA terminal debug logs";
    }

    rpc aaa-clear-local-user-lockout {
        description "This RPC is to clear the user lockout";
        input  {
            leaf username  {
                type string {
                    length "2..15";
                }
                mandatory true;
                description "";
            }
        }
    }

}

/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-vrrp-types.yang
*
*/

module ipi-vrrp-types {

    yang-version 1.1;

    namespace   "http://www.ipinfusion.com/yang/ocnos/ipi-vrrp-types";

    prefix "ipi-vrrp-types";

    organization
        "IP Infusion Inc.";

    contact
        "Address: 3965 Freedom Circle, Suite 200, Santa Clara, CA 95054
         Phone: +1 408-400-1900
         E-mail: support@ipinfusion.com
         Web: http://www.ipinfusion.com/";

    description
        "Virtual Router Redundancy Protocol Types";


    revision "2021-09-03" {
        description "Update descriptions of attribute";
        reference "Initial Version";
    }

    revision "2021-06-18" {
        description "Restructured module in accordance with OpenConfig style";
        reference "Initial Version";
    }



    typedef  vrrp_error_reason_t {
        type enumeration {
            enum no-error {
                value 0;
                description "No error reason";
            }
            enum ip-ttl-error {
                value 1;
                description "IP TTL error reason";
            }
            enum version-error {
                value 2;
                description "VRRP version error reason";
            }
            enum checksum-error {
                value 3;
                description "VRRP checksum error reason";
            }
            enum virtual-router-id-error {
                value 4;
                description "VRRP router Id error reason";
            }
        }
        description "type definition for VRRP_ERROR_REASON_T";
    }

    typedef  vrrp_new_master_reason_t {
        type enumeration {
            enum not-master {
                value 0;
                description "Not master";
            }
            enum priority {
                value 1;
                description "New master due priority";
            }
            enum preempted {
                value 2;
                description "New master due preemption";
            }
            enum master-no-response {
                value 3;
                description "New master due non response from master";
            }
        }
        description "type definition for VRRP_NEW_MASTER_REASON_T";
    }

    typedef  vrrp_iface_status_t {
        type enumeration {
            enum down {
                value 0;
                description "Interface down";
            }
            enum up {
                value 1;
                description "Interface up";
            }
        }
        description "type definition for VRRP_IFACE_STATUS_T";
    }

    typedef  vrrp_member_state_t {
        type enumeration {
            enum joined {
                value 1;
                description "VRRP_IPV4_MCAST_JOINED";
            }
            enum left {
                value 2;
                description "VRRP_IPV4_MCAST_LEFT";
            }
        }
        description "type definition for VRRP_MEMBER_STATE_T";
    }

    typedef  vrrp_addr_family_t {
        type enumeration {
            enum ipv4 {
                value 1;
                description "VRRP IPV4 Address family";
            }
            enum ipv6 {
                value 2;
                description "VRRP IPV6 Address family";
            }
        }
        description "type definition for VRRP_ADDR_FAMILY_T";
    }

    typedef  vrrp_admin_state_t {
        type enumeration {
            enum down {
                value 0;
                description "Interface down";
            }
            enum up {
                value 1;
                description "Interface up";
            }
        }
        description "type definition for VRRP_ADMIN_STATE_T";
    }

    typedef  vrrp_init_message_code_t {
        type enumeration {
            enum admin-down {
                value 0;
                description "(admin state down)";
            }
            enum if-not-running {
                value 1;
                description "(interface is not running)";
            }
            enum circuit-down {
                value 2;
                description "(monitored circuit is down)";
            }
            enum no-subnet {
                value 3;
                description "(no matching subnet)";
            }
            enum vip-unset {
                value 4;
                description "(virtual IP address not set)";
            }
            enum switch-back-delay {
                value 5;
                description "(In Switch Back Delay)";
            }
        }
        description "type definition for VRRP_INIT_MESSAGE_CODE_T";
    }

    typedef  vrrp_session_state_t {
        type enumeration {
            enum unknown {
                value 0;
                description "VRRP State Unknown";
            }
            enum init {
                value 1;
                description "VRRP State Init";
            }
            enum backup {
                value 2;
                description "VRRP State Backup";
            }
            enum master {
                value 3;
                description "VRRP State Master";
            }
        }
        description "type definition for VRRP_SESSION_STATE_T";
    }

    typedef  vrrp_ip_status_t {
        type enumeration {
            enum set {
                value 1;
                description "VRRP Address Set";
            }
            enum unset {
                value 2;
                description "VRRP Address Unset";
            }
        }
        description "type definition for VRRP_IP_STATUS_T";
    }

    typedef  vrrp_debug_t {
        type bits {
            bit events {
                position 1;
                description "VRRP events";
            }
            bit packet-send {
                position 2;
                description "VRRP packets,VRRP send packets";
            }
            bit packet-recv {
                position 3;
                description "VRRP packets,VRRP receive packets";
            }
        }
        description "type definition for VRRP_DEBUG_T";
    }

}

/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-mpls-rib.yang
*
*/

module ipi-mpls-rib {

    yang-version 1.1;

    namespace   "http://www.ipinfusion.com/yang/ocnos/ipi-mpls-rib";

    prefix "ipi-mpls-rib";

    import ietf-inet-types {
        prefix inet;
        revision-date 2013-07-15;
    }

    import ipi-interface {
        prefix ipi-interface;
        revision-date 2022-04-05;
    }

    import ipi-network-instance {
        prefix ipi-network-instance;
        revision-date 2021-11-10;
    }

    import ipi-vrf {
        prefix ipi-vrf;
        revision-date 2021-09-03;
    }

    import ipi-mpls {
        prefix ipi-mpls;
        revision-date 2022-04-22;
    }

    import ipi-mpls-types {
        prefix ipi-mpls-types;
        revision-date 2022-02-15;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "Data model for MPLS RIB";


    revision "2022-04-22" {
        description "Suncom patch merge";
        reference " 0.8.1.";
    }

    revision "2022-01-24" {
        description "Added backup nhlfe support for FTN Entries";
        reference " 0.8.0.";
    }

    revision "2021-06-26" {
        description "Added multipath runtime attribute for FTN Entries";
        reference " 0.7.0.";
    }

    revision "2021-06-24" {
        description "Added Service Mapping runtime attributes for FTN Entries";
        reference " 0.6.3.";
    }

    revision "2021-05-27" {
        description "Added tunnel-id as RDN for ipv4/ipv6 global/vrf ftn tables, introduced evpn-id";
        reference " 0.6.2.";
    }

    revision "2021-04-18" {
        description "Added ELC runtime attribute for FTN Entries";
        reference " 0.6.1.";
    }

    revision "2021-03-22" {
        description "Added IPv6 MPLS RIB run time attributes";
        reference " 0.6.0.";
    }

    revision "2021-03-15" {
        description "Change for restructuring LSP-Tunnel";
        reference " 0.5.0.";
    }

    revision "2021-03-04" {
        description "Added attribute pseudowire-id";
        reference " 0.4.0.";
    }

    revision "2021-02-12" {
        description "Netconf datamodel restructuring for Static ILM/FTN";
        reference " 0.4.0.";
    }

    revision "2020-12-15" {
        description "Change to have data-types in lower case instead of camel case";
        reference " 0.3.0.";
    }

    revision "2020-12-07" {
        description "MPLS-RIB-DROP2";
        reference " 0.2.0.";
    }

    revision "2020-11-03" {
        description "Initial Version";
        reference " 0.1.0.";
    }



    grouping vrf-grouping {
    description
        "mpls VRF";
        list vrf {
            if-feature feature-list:HAVE_VRF;
            key "vrf-name";
            config false;
            description
                "mpls VRF";
            leaf vrf-name  {
                type  leafref {
                    path  "../rib/vrf-name";
                }
                description "VRF instance name";
            } // END of vrf-name definition.

            container rib {
                config false;
                description
                    "MPLS rib parameters for VRF";
                container ftn-table {
                    config false;
                    description
                        "Per VRF IPv4 FTN entries";

                    list ipv4-ftn-entry {
                        key "fec-prefix owner lsp-type tunnel-id";
                        config false;
                        description
                            "IPv4 FTN entry";
                        leaf fec-prefix  {
                            type  leafref {
                                path  "../state/fec-prefix";
                            }
                            description "Forwarding Equivalence Class";
                        } // END of fec-prefix definition.

                        leaf owner  {
                            type  leafref {
                                path  "../state/owner";
                            }
                            description "The protocol module which installed this entry";
                        } // END of owner definition.

                        leaf lsp-type  {
                            type  leafref {
                                path  "../state/lsp-type";
                            }
                            description "Type of Label Switched Path";
                        } // END of lsp-type definition.

                        leaf tunnel-id  {
                            type  leafref {
                                path  "../state/tunnel-id";
                            }
                            description "RSVP tunnel id for which this entry is added";
                        } // END of tunnel-id definition.


                        list nhlfe-entry {
                            key "out-interface out-label";
                            config false;
                            description
                                "NHLFE entry";
                            leaf out-interface  {
                                type  leafref {
                                    path  "../state/out-interface";
                                }
                                description "Interface through which the packet should be forwarded";
                            } // END of out-interface definition.

                            leaf out-label  {
                                type  leafref {
                                    path  "../state/out-label";
                                }
                                description "Label value that is pushed to the outgoing MPLS header";
                            } // END of out-label definition.

                            container state {
                                config false;
                                description
                                    "Container for FTN NHLFE operational state";
                                uses mpls-rib-ipv4-ftn-nhlfe-entry-state;
                                uses mpls-rib-ip-ftn-nhlfe-entry-state;
                            } // END of state-container definition.
                        } // End of nhlfe-entry-list
                        container state {
                            config false;
                            description
                                "Container for FTN entry operational state";
                            uses mpls-rib-ipv4-ftn-entry-state;
                            uses mpls-rib-ip-ftn-entry-state;
                        } // END of state-container definition.
                    } // End of ipv4-ftn-entry-list

                    list ipv6-ftn-entry {
                        if-feature feature-list:HAVE_IPV6;
                        key "fec-prefix6 owner lsp-type tunnel-id";
                        config false;
                        description
                            "IPv6 FTN entry";
                        leaf fec-prefix6  {
                            type  leafref {
                                path  "../state/fec-prefix6";
                            }
                            description "Forwarding Equivalence Class for IP packet network";
                        } // END of fec-prefix6 definition.

                        leaf owner  {
                            type  leafref {
                                path  "../state/owner";
                            }
                            description "The protocol module which installed this entry";
                        } // END of owner definition.

                        leaf lsp-type  {
                            type  leafref {
                                path  "../state/lsp-type";
                            }
                            description "Type of Label Switched Path";
                        } // END of lsp-type definition.

                        leaf tunnel-id  {
                            type  leafref {
                                path  "../state/tunnel-id";
                            }
                            description "RSVP tunnel id for which this entry is added";
                        } // END of tunnel-id definition.


                        list nhlfe-entry {
                            key "out-interface out-label";
                            config false;
                            description
                                "NHLFE entry";
                            leaf out-interface  {
                                type  leafref {
                                    path  "../state/out-interface";
                                }
                                description "Interface through which the packet should be forwarded";
                            } // END of out-interface definition.

                            leaf out-label  {
                                type  leafref {
                                    path  "../state/out-label";
                                }
                                description "Label value that is pushed to the outgoing MPLS header";
                            } // END of out-label definition.

                            container state {
                                config false;
                                description
                                    "Container for FTN NHLFE operational state";
                                uses mpls-rib-ipv6-ftn-nhlfe-entry-state;
                                uses mpls-rib-ip-ftn-nhlfe-entry-state;
                            } // END of state-container definition.
                        } // End of nhlfe-entry-list
                        container state {
                            config false;
                            description
                                "Container for FTN entry operational state";
                            uses mpls-rib-ipv6-ftn-entry-state;
                            uses mpls-rib-ip-ftn-entry-state;
                        } // END of state-container definition.
                    } // End of ipv6-ftn-entry-list
                } // END of ftn-table-container definition.
                uses mpls-vrf-entry-state;
            } // END of rib-container definition.
        } // End of vrf-list
    } // END of vrf-grouping definition.
    grouping mpls-rib-ipv4-ftn-entry-state {
        description
            "mplsCMLSEPribCMLSEPipv4CMLSEPftnCMLSEPentryCMLSEPstate";
        leaf fec-prefix  {
            type  inet:ipv4-prefix;
            description "Forwarding Equivalence Class";
        } // END of fec-prefix definition.

        leaf owner  {
            type  ipi-mpls-types:mpls_rib_entry_owner_t;
            description "The protocol module which installed this entry";
        } // END of owner definition.

    } // END of mpls-rib-ipv4-ftn-entry-state definition.
    grouping mpls-rib-ipv6-ftn-entry-state {
        description
            "mplsCMLSEPribCMLSEPipv6CMLSEPftnCMLSEPentryCMLSEPstate";
        leaf fec-prefix6  {
            type  inet:ipv6-prefix;
            description "Forwarding Equivalence Class";
        } // END of fec-prefix6 definition.

        leaf owner  {
            type  ipi-mpls-types:mpls_rib_entry_owner_t;
            description "The protocol module which installed this entry";
        } // END of owner definition.

    } // END of mpls-rib-ipv6-ftn-entry-state definition.
    grouping mpls-rib-ip-ftn-entry-state {
        description
            "mplsCMLSEPribCMLSEPipCMLSEPftnCMLSEPentryCMLSEPstate";
        leaf lsp-type  {
            type  ipi-mpls-types:mpls_rib_lsp_type_t;
            description "Type of Label Switched Path";
        } // END of lsp-type definition.

        leaf ftn-index  {
            type  uint32;
            description "Unique system assigned index for the entry in FTN table";
        } // END of ftn-index definition.

        leaf is-primary  {
            type  boolean;
            description "Primary FTN entry";
        } // END of is-primary definition.

        leaf route-distance  {
            type  uint8;
            description "Route distance determined by the protocol module";
        } // END of route-distance definition.

        leaf redirect-action-type  {
            type  ipi-mpls-types:mpls_rib_action_type_t;
            description "redirection action to be performed on the packet";
        } // END of redirect-action-type definition.

        leaf qos-exp-bits  {
            type  uint8;
            description "QoS exp bit that is mapped to this entry";
        } // END of qos-exp-bits definition.

        leaf is-entropy-label  {
            type  boolean;
            description "Entropy Label Capability Flag";
        } // END of is-entropy-label definition.

        leaf in-dscp-class-name  {
            type  string {
                length "1..1965";
                pattern "[^?' =,>|]+";
            }
            description "Incoming DSCP value that is mapped to this entry";
        } // END of in-dscp-class-name definition.

        leaf tunnel-id  {
            type  uint32;
            description "RSVP tunnel id for which this entry is added";
        } // END of tunnel-id definition.

        leaf protected-lsp-id  {
            type  uint32;
            description "Identifier for the protected LSP, applicable only when LSP protection
                        is enabled for RSVP trunk";
        } // END of protected-lsp-id definition.

        leaf qos-resource-id  {
            type  uint32;
            description "Qos resource id";
        } // END of qos-resource-id definition.

        leaf color  {
            if-feature feature-list:HAVE_MPLS_SERVICE_MAPPING;
            type  uint32;
            description "Tunnel FTN color";
        } // END of color definition.

        leaf tunnel-policy-name  {
            if-feature feature-list:HAVE_MPLS_SERVICE_MAPPING;
            type  string {
                length "1..1965";
                pattern "[^?' =,>|]+";
            }
            description "Tunnel policy name that the Service FTN associated";
        } // END of tunnel-policy-name definition.

        leaf rsvp-multipath-name  {
            if-feature feature-list:HAVE_RSVP_MULTIPATH;
            type  string {
                length "1..1965";
                pattern "[^?' =,>|]+";
            }
            description "RSVP multipath group name associated with RSVP FTN";
        } // END of rsvp-multipath-name definition.

    } // END of mpls-rib-ip-ftn-entry-state definition.
    grouping mpls-rib-ipv4-ftn-nhlfe-entry-state {
        description
            "mplsCMLSEPribCMLSEPipv4CMLSEPftnCMLSEPnhlfeCMLSEPentryCMLSEPstate";
        leaf out-interface  {
            type  leafref {
                path  "/ipi-interface:interfaces/ipi-interface:interface/ipi-interface:name";
            }
            description "Interface through which the packet should be forwarded";
        } // END of out-interface definition.

        leaf out-label  {
            type  uint32;
            description "Label value that is pushed to the outgoing MPLS header";
        } // END of out-label definition.

        leaf nexthop-address  {
            type  inet:ipv4-address;
            description "IP address of the next hop";
        } // END of nexthop-address definition.

        leaf nhlfe-type  {
            type  ipi-mpls-types:mpls_rib_nhlfe_type_t;
            description "Type of the next hop";
        } // END of nhlfe-type definition.

    } // END of mpls-rib-ipv4-ftn-nhlfe-entry-state definition.
    grouping mpls-rib-ipv6-ftn-nhlfe-entry-state {
        description
            "mplsCMLSEPribCMLSEPipv6CMLSEPftnCMLSEPnhlfeCMLSEPentryCMLSEPstate";
        leaf out-interface  {
            type  leafref {
                path  "/ipi-interface:interfaces/ipi-interface:interface/ipi-interface:name";
            }
            description "Interface through which the packet should be forwarded";
        } // END of out-interface definition.

        leaf out-label  {
            type  uint32;
            description "Label value that is pushed to the outgoing MPLS header";
        } // END of out-label definition.

        leaf nexthop-address  {
            type  inet:ip-address;
            description "IP address of the next hop";
        } // END of nexthop-address definition.

        leaf nhlfe-type  {
            type  ipi-mpls-types:mpls_rib_nhlfe_type_t;
            description "Type of the next hop";
        } // END of nhlfe-type definition.

    } // END of mpls-rib-ipv6-ftn-nhlfe-entry-state definition.
    grouping mpls-rib-ip-ftn-nhlfe-entry-state {
        description
            "mplsCMLSEPribCMLSEPipCMLSEPftnCMLSEPnhlfeCMLSEPentryCMLSEPstate";
        leaf administrative-status  {
            type  ipi-mpls-types:mpls_rib_entry_admin_status_t;
            description "Administrative status of this FTN NHLFE entry";
        } // END of administrative-status definition.

        leaf oper-status  {
            type  ipi-mpls-types:mpls_rib_entry_oper_status_t;
            description "Oper status of this FTN NHLFE entry";
        } // END of oper-status definition.

        leaf nhlfe-owner  {
            type  ipi-mpls-types:mpls_rib_entry_owner_t;
            description "Protocol Module that installed this nhlfe entry";
        } // END of nhlfe-owner definition.

        leaf nhlfe-index  {
            type  uint32;
            description "System assigned index for this NHLFE entry";
        } // END of nhlfe-index definition.

        leaf is-stale  {
            type  boolean;
            description "A deleted NHLFE entry for which clean-up is pending";
        } // END of is-stale definition.

        leaf label-op-code  {
            type  ipi-mpls-types:mpls_rib_label_op_code_t;
            description "Action to be performed on the MPLS label stack";
        } // END of label-op-code definition.

    } // END of mpls-rib-ip-ftn-nhlfe-entry-state definition.
    grouping mpls-rib-ip-ilm-nhlfe-entry-state {
        description
            "mplsCMLSEPribCMLSEPipCMLSEPilmCMLSEPnhlfeCMLSEPentryCMLSEPstate";
        leaf out-interface  {
            type  leafref {
                path  "/ipi-interface:interfaces/ipi-interface:interface/ipi-interface:name";
            }
            description "Interface through which the packet should be forwarded";
        } // END of out-interface definition.

        leaf out-label  {
            type  uint32;
            description "Label value that is pushed to the outgoing MPLS header";
        } // END of out-label definition.

        leaf nexthop-address  {
            type  inet:ip-address;
            description "IP address of the next hop";
        } // END of nexthop-address definition.

        leaf nhlfe-owner  {
            type  ipi-mpls-types:mpls_rib_entry_owner_t;
            description "Protocol Module that installed this nhlfe entry";
        } // END of nhlfe-owner definition.

        leaf nhlfe-index  {
            type  uint32;
            description "System assigned index for this NHLFE entry";
        } // END of nhlfe-index definition.

        leaf label-op-code  {
            type  ipi-mpls-types:mpls_rib_label_op_code_t;
            description "Action to be performed on the MPLS label stack";
        } // END of label-op-code definition.

    } // END of mpls-rib-ip-ilm-nhlfe-entry-state definition.
    grouping mpls-vrf-entry-state {
        description
            "VRF entry operational state data";
        leaf vrf-name  {
            type  leafref {
                path  "/ipi-network-instance:network-instances/ipi-network-instance:network-instance/ipi-vrf:vrf/ipi-vrf:config/ipi-vrf:vrf-name";
            }
            description "VRF instance name";
        } // END of vrf-name definition.

    } // END of mpls-vrf-entry-state definition.
    grouping mpls-rib-ip-ilm-entry-state {
        description
            "ILM entry operational state";
        leaf in-interface  {
            type  leafref {
                path  "/ipi-interface:interfaces/ipi-interface:interface/ipi-interface:name";
            }
            description "Interface on which the MPLS packet is recieved";
        } // END of in-interface definition.

        leaf in-label  {
            type  uint32;
            description "MPLS label in the incoming packet header";
        } // END of in-label definition.

        leaf vrf-name  {
            type  leafref {
                path  "/ipi-network-instance:network-instances/ipi-network-instance:network-instance/ipi-vrf:vrf/ipi-vrf:config/ipi-vrf:vrf-name";
            }
            description "VRF instance name";
        } // END of vrf-name definition.

        leaf owner  {
            type  ipi-mpls-types:mpls_rib_entry_owner_t;
            description "The protocol module which installed this entry";
        } // END of owner definition.

        leaf ilm-index  {
            type  uint32;
            description "Unique system assigned index for this entry in ilm table";
        } // END of ilm-index definition.

        leaf is-stitched-to-ftn  {
            type  boolean;
            description "is this entry stitched to an FTN entry";
        } // END of is-stitched-to-ftn definition.

        leaf is-installed-in-fib  {
            type  boolean;
            description "is this entry succesfully installed in Forwarding Table";
        } // END of is-installed-in-fib definition.

        leaf is-selected  {
            type  boolean;
            description "is this entry updated to Forwarding Table";
        } // END of is-selected definition.

        leaf is-stale  {
            type  boolean;
            description "A deleted entry for which clean-up is pending";
        } // END of is-stale definition.

        leaf fec-prefix  {
            type  inet:ip-prefix;
            description "Forwarding Equivalence Class";
        } // END of fec-prefix definition.

        leaf label-op-code  {
            type  ipi-mpls-types:mpls_rib_label_op_code_t;
            description "Action to be performed on the MPLS label stack";
        } // END of label-op-code definition.

        leaf pseudowire-id  {
            type  uint32;
            description "pseudowire for which this ILM entry is added";
        } // END of pseudowire-id definition.

        leaf evpn-id  {
            if-feature feature-list:HAVE_BGP_EVPN;
            if-feature feature-list:HAVE_NVO;
            type  uint32;
            description "EVPN id for which this ILM entry is added";
        } // END of evpn-id definition.

    } // END of mpls-rib-ip-ilm-entry-state definition.
    grouping mpls-static-ipv4-map-route-config {
        description
            "MPLS Static IPv4 Map Route Configurations";
        leaf route-prefix  {
            type  inet:ipv4-prefix;
            description "Use this attribute to specify the route prefix for which FEC mapping
                        needs to be added";
        } // END of route-prefix definition.

        leaf mapped-fec  {
            type  inet:ipv4-prefix;
            mandatory true;
            description "Use this attribute to specify the FEC prefix that is mapped to the
                        route";
        } // END of mapped-fec definition.

    } // END of mpls-static-ipv4-map-route-config definition.
    grouping mpls-tp-ipv4-map-route-config {
        description
            "MPLS TP Map Route Configuration";
        leaf route-prefix  {
            type  inet:ipv4-prefix;
            description "Use this attribute to specify the route prefix for which Tunnel
                        Mapping needs to be added";
        } // END of route-prefix definition.

        leaf mapped-tunnel-name  {
            type  string {
                length "1..1965";
                pattern "[^?' =,>|]+";
            }
            mandatory true;
            description "Use this attribute to specify the Tunnel Name that is mapped to the
                        prefix";
        } // END of mapped-tunnel-name definition.

    } // END of mpls-tp-ipv4-map-route-config definition.
    grouping mpls-static-ipv4-lsp-tunnel-config {
        description
            "MPLS Static IPv4 LSP tunnel Configurations";
        leaf in-interface-name  {
            type  string {
                length "1..1965";
                pattern "[^?' =,>|]+";
            }
            description "Incoming Interface Name. Use this attribute to choose the transit LSP
                        and a locally configured LSP tunnel for carrying the transit LSP";
        } // END of in-interface-name definition.

        leaf incoming-label  {
            type  leafref {
                path  "/ipi-interface:interfaces/ipi-interface:interface/ipi-interface:name";
            }
            description "Incoming Label - Use this attribute to choose the transit LSP and a
                        locally configured LSP tunnel for carrying the transit LSP";
        } // END of incoming-label definition.

        leaf pushed-label  {
            type  uint32 {
                 range "16..1048575"  {
                    description "16..1048575:Out-going Label <16-1048575>";
                 }
            }
            mandatory true;
            description "Use this attribute to specify the pushed label for the tunnel";
        } // END of pushed-label definition.

        leaf fec-prefix  {
            type  inet:ipv4-prefix;
            mandatory true;
            description "Use this attribute to specify the FEC prefix for the tunnel";
        } // END of fec-prefix definition.

    } // END of mpls-static-ipv4-lsp-tunnel-config definition.
    grouping mpls-ipv4-static-ftn-config {
        description
            "MPLS Static IPv4 FTN Configurations";
        leaf fec-prefix  {
            type  inet:ipv4-prefix;
            description "Forwarding Equivalence Class";
        } // END of fec-prefix definition.

        leaf pushed-label  {
            type  uint32 {
                 range "16..1048575"  {
                    description "16..1048575:Out-going Label <16-1048575>";
                 }
            }
            description "Outgoing label value";
        } // END of pushed-label definition.

        leaf nexthop-ip-address  {
            type  inet:ipv4-address;
            description "Nexthop IP address";
        } // END of nexthop-ip-address definition.

        leaf out-interface-name  {
            type  leafref {
                path  "/ipi-interface:interfaces/ipi-interface:interface/ipi-interface:name";
            }
            description "Outgoing interface name";
        } // END of out-interface-name definition.

    } // END of mpls-ipv4-static-ftn-config definition.
    grouping mpls-static-ftn-tunnel-config {
        description
            "MPLS Static FTN Tunnel Configurations";
        leaf tunnel-id  {
            type  uint32 {
                 range "1..5000"  {
                    description "1..5000:Tunnel Id";
                 }
            }
            description "FTN tunnel-id value";
        } // END of tunnel-id definition.

        leaf fec-prefix  {
            type  inet:ip-prefix;
            description "Forwarding Equivalence Class";
        } // END of fec-prefix definition.

        leaf pushed-label  {
            type  uint32 {
                 range "16..1048575"  {
                    description "16..1048575:Out-going Label <16-1048575>";
                 }
            }
            description "Outgoing label value";
        } // END of pushed-label definition.

        leaf nexthop-ip-address  {
            type  inet:ip-address;
            description "Nexthop IP address";
        } // END of nexthop-ip-address definition.

        leaf out-interface-name  {
            type  leafref {
                path  "/ipi-interface:interfaces/ipi-interface:interface/ipi-interface:name";
            }
            description "Outgoing interface name";
        } // END of out-interface-name definition.

        leaf is-primary  {
            type  ipi-mpls-types:mpls_vpls_ftn_entry_lsp_type_t;
            description "Primary FTN entry";
        } // END of is-primary definition.

    } // END of mpls-static-ftn-tunnel-config definition.
    grouping mpls-static-ilm-pop-config {
        description
            "MPLS Static ILM POP Entries";
        leaf enable-pop-label  {
            type  empty;
            mandatory true;
            description "Use this attribute to create an ILM entry in the ILM table to which a
                        POP incoming interface is bound. Upon receipt of  a labeled packet on
                        an MPLS-enabled router, a lookup is done based on the incoming label
                        in the ILM table. If a match is found, the packet may either be
                        label-switched downstream, or popped and passed over IP. In a pop
                        operation, an outgoing label is not needed as is either accepted or
                        forwarded over IP. The nexthop option is also not mandatory because
                        the FEC IP address could be a local IP address";
        } // END of enable-pop-label definition.

    } // END of mpls-static-ilm-pop-config definition.
    grouping mpls-static-ilm-swap-config {
        description
            "MPLS Static ILM SWAP Entries";
        leaf in-interface-name  {
            type  string {
                length "1..1965";
                pattern "[^?' =,>|]+";
            }
            description "Incoming Interface Name";
        } // END of in-interface-name definition.

        leaf swapped-label  {
            type  uint32 {
                 range "16..1048575"  {
                    description "16..1048575:Out-going Label <16-1048575>";
                 }
            }
            description "Outgoing Label";
        } // END of swapped-label definition.

        leaf out-interface-name  {
            type  leafref {
                path  "/ipi-interface:interfaces/ipi-interface:interface/ipi-interface:name";
            }
            description "Outgoing Interface Name";
        } // END of out-interface-name definition.

        leaf nexthop-ip-address  {
            type  inet:ip-address;
            description "Nexthop IP Address";
        } // END of nexthop-ip-address definition.

        leaf fec-prefix  {
            type  inet:ip-prefix;
            description "FEC Prefix for which the ILM entry is configured";
        } // END of fec-prefix definition.

    } // END of mpls-static-ilm-swap-config definition.
    grouping mpls-static-ilm-config {
        description
            "MPLS Static ILM Entries";
        leaf incoming-label  {
            type  uint32 {
                 range "16..1048575"  {
                    description "16..1048575:in-coming Label <16-1048575>";
                 }
            }
            description "Incoming Label";
        } // END of incoming-label definition.

    } // END of mpls-static-ilm-config definition.
    grouping mpls-rsvp-multipath-group-state {
        description
            "mplsCMLSEPrsvpCMLSEPmultipathCMLSEPgroupCMLSEPstate";
        leaf multipath-identifier  {
            type  uint16;
            description "Identifier of RSVP multipath group";
        } // END of multipath-identifier definition.

        leaf multipath-name  {
            type  string {
                length "1..1965";
                pattern "[^?' =,>|]+";
            }
            description "Name of RSVP multipath group";
        } // END of multipath-name definition.

        leaf multipath-nhlfe-index  {
            type  uint32;
            description "NHLFE identifier for RSVP multipath group";
        } // END of multipath-nhlfe-index definition.

        leaf fec-prefix  {
            type  inet:ipv4-prefix;
            description "Forwarding Equivalence Class of RSVP multipath group";
        } // END of fec-prefix definition.

        leaf active-member-count  {
            type  uint16;
            description "Number of active mutlipath group members";
        } // END of active-member-count definition.

    } // END of mpls-rsvp-multipath-group-state definition.

    grouping  rib-grouping {
    description
        "Top level container for MPLS rib , including configuration and state
                data";
    container rib {
        description
            "Top level container for MPLS rib , including configuration and state
                    data";
        container global-ftn-table {
            config false;
            description
                "Global FTN table";

            list ipv4-ftn-entry {
                key "fec-prefix owner lsp-type tunnel-id";
                config false;
                description
                    "Global IPv4 FTN entries";
                leaf fec-prefix  {
                    type  leafref {
                        path  "../state/fec-prefix";
                    }
                    description "Forwarding Equivalence Class";
                } // END of fec-prefix definition.

                leaf owner  {
                    type  leafref {
                        path  "../state/owner";
                    }
                    description "The protocol module which installed this entry";
                } // END of owner definition.

                leaf lsp-type  {
                    type  leafref {
                        path  "../state/lsp-type";
                    }
                    description "Type of Label Switched Path";
                } // END of lsp-type definition.

                leaf tunnel-id  {
                    type  leafref {
                        path  "../state/tunnel-id";
                    }
                    description "RSVP tunnel id for which this entry is added";
                } // END of tunnel-id definition.


                list nhlfe-entry {
                    key "out-interface out-label administrative-status";
                    config false;
                    description
                        "NHLFE entry";
                    leaf out-interface  {
                        type  leafref {
                            path  "../state/out-interface";
                        }
                        description "Interface through which the packet should be forwarded";
                    } // END of out-interface definition.

                    leaf out-label  {
                        type  leafref {
                            path  "../state/out-label";
                        }
                        description "Label value that is pushed to the outgoing MPLS header";
                    } // END of out-label definition.

                    leaf administrative-status  {
                        type  leafref {
                            path  "../state/administrative-status";
                        }
                        description "Administrative status of this FTN NHLFE entry";
                    } // END of administrative-status definition.

                    container state {
                        config false;
                        description
                            "Container for FTN NHLFE entry operational state";
                        uses mpls-rib-ipv4-ftn-nhlfe-entry-state;
                        uses mpls-rib-ip-ftn-nhlfe-entry-state;
                    } // END of state-container definition.
                } // End of nhlfe-entry-list
                container state {
                    config false;
                    description
                        "Container for FTN entry operational state";
                    uses mpls-rib-ipv4-ftn-entry-state;
                    uses mpls-rib-ip-ftn-entry-state;
                } // END of state-container definition.
            } // End of ipv4-ftn-entry-list

            list ipv6-ftn-entry {
                if-feature feature-list:HAVE_IPV6;
                key "fec-prefix6 owner lsp-type tunnel-id";
                config false;
                description
                    "Global IPv6 FTN entries";
                leaf fec-prefix6  {
                    type  leafref {
                        path  "../state/fec-prefix6";
                    }
                    description "Forwarding Equivalence Class for IP packet network";
                } // END of fec-prefix6 definition.

                leaf owner  {
                    type  leafref {
                        path  "../state/owner";
                    }
                    description "The protocol module which installed this entry";
                } // END of owner definition.

                leaf lsp-type  {
                    type  leafref {
                        path  "../state/lsp-type";
                    }
                    description "Type of Label Switched Path";
                } // END of lsp-type definition.

                leaf tunnel-id  {
                    type  leafref {
                        path  "../state/tunnel-id";
                    }
                    description "RSVP tunnel id for which this entry is added";
                } // END of tunnel-id definition.


                list nhlfe-entry {
                    key "out-interface out-label administrative-status";
                    config false;
                    description
                        "NHLFE entry";
                    leaf out-interface  {
                        type  leafref {
                            path  "../state/out-interface";
                        }
                        description "Interface through which the packet should be forwarded";
                    } // END of out-interface definition.

                    leaf out-label  {
                        type  leafref {
                            path  "../state/out-label";
                        }
                        description "Label value that is pushed to the outgoing MPLS header";
                    } // END of out-label definition.

                    leaf administrative-status  {
                        type  leafref {
                            path  "../state/administrative-status";
                        }
                        description "Administrative status of this FTN NHLFE entry";
                    } // END of administrative-status definition.

                    container state {
                        config false;
                        description
                            "Container for FTN NHLFE entry operational state";
                        uses mpls-rib-ipv6-ftn-nhlfe-entry-state;
                        uses mpls-rib-ip-ftn-nhlfe-entry-state;
                    } // END of state-container definition.
                } // End of nhlfe-entry-list
                container state {
                    config false;
                    description
                        "Container for FTN entry operational state";
                    uses mpls-rib-ipv6-ftn-entry-state;
                    uses mpls-rib-ip-ftn-entry-state;
                } // END of state-container definition.
            } // End of ipv6-ftn-entry-list
        } // END of global-ftn-table-container definition.
        container ilm-table {
            config false;
            description
                "ILM table";

            list ip-ilm-entry {
                key "in-interface in-label";
                config false;
                description
                    "IP ILM entries";
                leaf in-interface  {
                    type  leafref {
                        path  "../state/in-interface";
                    }
                    description "Interface on which the MPLS packet is recieved";
                } // END of in-interface definition.

                leaf in-label  {
                    type  leafref {
                        path  "../state/in-label";
                    }
                    description "MPLS label in the incoming packet header";
                } // END of in-label definition.


                list nhlfe-entry {
                    key "out-interface out-label";
                    config false;
                    description
                        "NHLFE entries per ILM entry";
                    leaf out-interface  {
                        type  leafref {
                            path  "../state/out-interface";
                        }
                        description "Interface through which the packet should be forwarded";
                    } // END of out-interface definition.

                    leaf out-label  {
                        type  leafref {
                            path  "../state/out-label";
                        }
                        description "Label value that is pushed to the outgoing MPLS header";
                    } // END of out-label definition.

                    container state {
                        config false;
                        description
                            "Container for FTN NHLFE operational state";
                        uses mpls-rib-ip-ilm-nhlfe-entry-state;
                    } // END of state-container definition.
                } // End of nhlfe-entry-list
                container state {
                    config false;
                    description
                        "Container for ILM entry operational state";
                    uses mpls-rib-ip-ilm-entry-state;
                } // END of state-container definition.
            } // End of ip-ilm-entry-list
        } // END of ilm-table-container definition.
        container rsvp-multipath-table {
            if-feature feature-list:HAVE_RSVP_MULTIPATH;
            config false;
            description
                "RSVP multipath group table";

            list rsvp-multipath-entry {
                key "multipath-identifier";
                config false;
                description
                    "RSVP multipath group entries";
                leaf multipath-identifier  {
                    type  leafref {
                        path  "../state/multipath-identifier";
                    }
                    description "Identifier of RSVP multipath group";
                } // END of multipath-identifier definition.

                container state {
                    config false;
                    description
                        "Container for FTN entry operational state";
                    uses mpls-rsvp-multipath-group-state;
                } // END of state-container definition.
            } // End of rsvp-multipath-entry-list
        } // END of rsvp-multipath-table-container definition.
        container map-route {
            description
                "MPLS Map Route";

            list static-ipv4-map-route {
                key "route-prefix";
                description
                    "MPLS Static IPv4 Map Route Entries";
                leaf route-prefix  {
                    type  leafref {
                        path  "../config/route-prefix";
                    }
                    description "Use this attribute to specify the route prefix for which FEC mapping
                                needs to be added";
                } // END of route-prefix definition.

                container config {
                    description
                        "Config Container for MPLS Map Route";
                    uses mpls-static-ipv4-map-route-config;
                } // END of config-container definition.
                container state {
                    config false;
                    description
                        "State Container for MPLS Map Route";
                    uses mpls-static-ipv4-map-route-config;
                } // END of state-container definition.
            } // End of static-ipv4-map-route-list
        } // END of map-route-container definition.
        container static-lsps {
            description
                "MPLS LSP Entries";

            list ipv4-static-ftn-entry {
                key "fec-prefix pushed-label nexthop-ip-address out-interface-name";
                description
                    "MPLS Static IPv4 FTN Entries";
                leaf fec-prefix  {
                    type  leafref {
                        path  "../config/fec-prefix";
                    }
                    description "Forwarding Equivalence Class";
                } // END of fec-prefix definition.

                leaf pushed-label  {
                    type  leafref {
                        path  "../config/pushed-label";
                    }
                    description "Outgoing label value";
                } // END of pushed-label definition.

                leaf nexthop-ip-address  {
                    type  leafref {
                        path  "../config/nexthop-ip-address";
                    }
                    description "Nexthop IP address";
                } // END of nexthop-ip-address definition.

                leaf out-interface-name  {
                    type  leafref {
                        path  "../config/out-interface-name";
                    }
                    description "Outgoing interface name";
                } // END of out-interface-name definition.

                container config {
                    description
                        "Config Container for MPLS Static IPv4 FTN Entries";
                    uses mpls-ipv4-static-ftn-config;
                } // END of config-container definition.
                container state {
                    config false;
                    description
                        "State Container for MPLS Static IPv4 FTN Entries";
                    uses mpls-ipv4-static-ftn-config;
                } // END of state-container definition.
            } // End of ipv4-static-ftn-entry-list

            list static-ftn-tunnel {
                if-feature feature-list:NOT_HAVE_MPLS_TUNNEL;
                key "tunnel-id fec-prefix pushed-label nexthop-ip-address out-interface-name is-primary";
                description
                    "MPLS Static IPv4/IPv6 FTN Tunnel Entries";
                leaf tunnel-id  {
                    type  leafref {
                        path  "../config/tunnel-id";
                    }
                    description "FTN tunnel-id value";
                } // END of tunnel-id definition.

                leaf fec-prefix  {
                    type  leafref {
                        path  "../config/fec-prefix";
                    }
                    description "Forwarding Equivalence Class";
                } // END of fec-prefix definition.

                leaf pushed-label  {
                    type  leafref {
                        path  "../config/pushed-label";
                    }
                    description "Outgoing label value";
                } // END of pushed-label definition.

                leaf nexthop-ip-address  {
                    type  leafref {
                        path  "../config/nexthop-ip-address";
                    }
                    description "Nexthop IP address";
                } // END of nexthop-ip-address definition.

                leaf out-interface-name  {
                    type  leafref {
                        path  "../config/out-interface-name";
                    }
                    description "Outgoing interface name";
                } // END of out-interface-name definition.

                leaf is-primary  {
                    type  leafref {
                        path  "../config/is-primary";
                    }
                    description "Primary FTN entry";
                } // END of is-primary definition.

                container config {
                    description
                        "Config Container for MPLS Static FTN Tunnel Entries";
                    uses mpls-static-ftn-tunnel-config;
                } // END of config-container definition.
                container state {
                    config false;
                    description
                        "State Container for MPLS Static FTN Tunnel Entries";
                    uses mpls-static-ftn-tunnel-config;
                } // END of state-container definition.
            } // End of static-ftn-tunnel-list

            list static-ilm-entry {
                key "incoming-label";
                description
                    "MPLS Static IPv4/IPv6 ILM Entries";
                leaf incoming-label  {
                    type  leafref {
                        path  "../config/incoming-label";
                    }
                    description "Incoming Label";
                } // END of incoming-label definition.


                list swap {
                    key "in-interface-name swapped-label out-interface-name nexthop-ip-address fec-prefix";
                    description
                        "MPLS ILM SWAP Entries";
                    leaf in-interface-name  {
                        type  leafref {
                            path  "../config/in-interface-name";
                        }
                        description "Incoming Interface Name";
                    } // END of in-interface-name definition.

                    leaf swapped-label  {
                        type  leafref {
                            path  "../config/swapped-label";
                        }
                        description "Outgoing Label";
                    } // END of swapped-label definition.

                    leaf out-interface-name  {
                        type  leafref {
                            path  "../config/out-interface-name";
                        }
                        description "Outgoing Interface Name";
                    } // END of out-interface-name definition.

                    leaf nexthop-ip-address  {
                        type  leafref {
                            path  "../config/nexthop-ip-address";
                        }
                        description "Nexthop IP Address";
                    } // END of nexthop-ip-address definition.

                    leaf fec-prefix  {
                        type  leafref {
                            path  "../config/fec-prefix";
                        }
                        description "FEC Prefix for which the ILM entry is configured";
                    } // END of fec-prefix definition.

                    container config {
                        description
                            "Config Container for MPLS ILM Swap Interface Entries";
                        uses mpls-static-ilm-swap-config;
                    } // END of config-container definition.
                    container state {
                        config false;
                        description
                            "State Container for MPLS ILM Swap Interface Entries";
                        uses mpls-static-ilm-swap-config;
                    } // END of state-container definition.
                } // End of swap-list
                container config {
                    description
                        "Config Container for MPLS Static ILM Entries";
                    uses mpls-static-ilm-config;
                } // END of config-container definition.
                container state {
                    config false;
                    description
                        "State Container for MPLS Static ILM Entries";
                    uses mpls-static-ilm-config;
                } // END of state-container definition.
                container pop {
                    description
                        "MPLS ILM POP Entries";
                    container config {
                        presence "To configure ILM POP Entries";
                        description
                            "Config Container for MPLS ILM POP Entries";
                        uses mpls-static-ilm-pop-config;
                    } // END of config-container definition.
                    container state {
                        config false;
                        description
                            "State Container for MPLS ILM POP Entries";
                        uses mpls-static-ilm-pop-config;
                    } // END of state-container definition.
                } // END of pop-container definition.
            } // End of static-ilm-entry-list
        } // END of static-lsps-container definition.
    } // END of rib-container definition.
    } // END of rib-grouping definition.

    augment /ipi-mpls:mpls {
        description
            "Top level container for MPLS rib , including configuration and state
                    data";
        uses rib-grouping;
    }

    augment /ipi-mpls:mpls {
        description
            "mpls VRF";
        uses vrf-grouping;
    }


}

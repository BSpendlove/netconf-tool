/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-l2vpn-vpls.yang
*
*/

module ipi-l2vpn-vpls {

    yang-version 1.1;

    namespace   "http://www.ipinfusion.com/yang/ocnos/ipi-l2vpn-vpls";

    prefix "ipi-l2vpn-vpls";

    import cml-data-types {
        prefix cml-data-types;
        revision-date 2022-04-04;
    }

    import ipi-vpls-types {
        prefix ipi-vpls-types;
        revision-date 2022-02-16;
    }

    import ietf-inet-types {
        prefix inet;
        revision-date 2013-07-15;
    }

    import ietf-yang-types {
        prefix yang;
        revision-date 2013-07-15;
    }

    import ipi-interface {
        prefix ipi-interface;
        revision-date 2022-04-05;
    }

    import ipi-network-instance {
        prefix ipi-network-instance;
        revision-date 2021-11-10;
    }

    import ipi-mpls {
        prefix ipi-mpls;
        revision-date 2022-04-22;
    }

    import ipi-qos {
        prefix ipi-qos;
        revision-date 2022-01-13;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-l2vpn-vpls";


    revision "2022-04-04" {
        description "Added if-feature whereever needed";
        reference " 0.7.0.";
    }

    revision "2022-01-20" {
        description "Updated RDN for ro objectlist network-interface-counters";
        reference " 0.6.4.";
    }

    revision "2021-12-30" {
        description "Updated length constraint for tunnel-name";
        reference " 0.6.3.";
    }

    revision "2021-12-28" {
        description "Added when constraints for vpls-peer tunnel-identifier,tunnel-name and tunnel-policy";
        reference " 0.6.2.";
    }

    revision "2021-12-20" {
        description "Updated datatype and range for tunnel-identifier";
        reference " 0.6.1.";
    }

    revision "2021-12-15" {
        description "Added VPLS counters related operational attributes";
        reference " 0.6.0.";
    }

    revision "2021-11-30" {
        description "Updated dependency condition for signaling-ldp on vpls-peer";
        reference " 0.5.1.";
    }

    revision "2021-11-16" {
        description "Adding L2CP support";
        reference " 0.5.0.";
    }

    revision "2021-09-06" {
        description "Removed the dependency of L2VPN VPLS configuration in subinterface with global L2VPN VPLS configurataion";
        reference " 0.4.0.";
    }

    revision "2021-08-03" {
        description "Added L2VPN VPLS attributes for Sub-interface";
        reference " 0.3.0.";
    }

    revision "2021-03-08" {
        description "Added Read-only attributes for vpls info, mac-addresses learnt, vpls-peer and statistics info";
        reference " 0.2.0.";
    }

    revision "2020-11-30" {
        description "Initial Version";
        reference " 0.1.0.";
    }

    grouping vpls-service-template-mapping-top {
        description
            "Top level Grouping for service template mapping to VPLS on AC
                        interface";

        list service-template-mapping {
            key "interface-name vpls-name service-template-name";
            description
                "Configuration data for Service Template mapping to VPLS on an
                            interface";
            leaf interface-name  {
                type  leafref {
                    path  "../config/interface-name";
                }
                description "This attribute specifies the attachment circuit interface to which the
                            service template is applied";
            } // END of interface-name definition.

            leaf vpls-name  {
                type  leafref {
                    path  "../config/vpls-name";
                }
                description "Specify VPLS instance name";
            } // END of vpls-name definition.

            leaf service-template-name  {
                type  leafref {
                    path  "../config/service-template-name";
                }
                description "Specify Customer service template name to bind to this Attachment
                            circuit";
            } // END of service-template-name definition.

            container config {
                description
                    "Configuration data for Attachment-Circuit";
                uses vpls-service-template-mapping-config;
            } // END of config-container definition.
            container state {
                config false;
                description
                    "Operation state data for Attachment-Circuit";
                uses vpls-service-template-mapping-config;
            } // END of state-container definition.
            uses virtual-circuit-quality-of-service-top;
        } // End of service-template-mapping-list
    } // END of vpls-service-template-mapping-top definition.
    grouping vpls-service-template-mapping-config {
        description
            "Grouping for VPLS Attachment-Circuit configuration";
        leaf interface-name  {
            type  leafref {
                path  "/ipi-interface:interfaces/ipi-interface:interface/ipi-interface:name";
            }
            description "This attribute specifies the attachment circuit interface to which the
                        service template is applied";
        } // END of interface-name definition.

        leaf service-template-name  {
            type  leafref {
                path  "/ipi-mpls:mpls/ipi-mpls:l2vpn/ipi-mpls:customer-service-template/ipi-mpls:config/ipi-mpls:name";
            }
            description "Specify Customer service template name to bind to this Attachment
                        circuit";
        } // END of service-template-name definition.

        leaf vpls-name  {
            type  string {
                length "1..1965";
                pattern "[^?' =,>|]+";
            }
            description "Specify VPLS instance name";
        } // END of vpls-name definition.

        leaf admin-status  {
            type  ipi-vpls-types:vpls_ac_admin_status_t;
            description "Specify admin status for VPLS AC";
        } // END of admin-status definition.

        leaf attachment-circuit-description  {
            type  cml-data-types:cml_line_t {
                length "1..1965";
            }
            description "Specify description of VPLS AC";
        } // END of attachment-circuit-description definition.

        leaf mac-learning  {
            type  ipi-vpls-types:vpls_mac_learning_t;
            description "Specify mac-learning for VPLS AC";
        } // END of mac-learning definition.

        leaf allow-layer2-bridge-pdu  {
            if-feature feature-list:HAVE_CUSTOM1_MPLS;
            type  empty;
            description "Specify allowed L2 control packets in peer-mode";
        } // END of allow-layer2-bridge-pdu definition.

        leaf-list static-mac-address  {
            type  cml-data-types:cml_mac_addr_t {
                length "1..1965";
            }
            description "Specify static-mac to be added on AC";
        } // END of static-mac-address definition.

    } // END of vpls-service-template-mapping-config definition.
    grouping virtual-circuit-quality-of-service-top {
        description
            "Top level grouping for VPLS QOS Profile on AC";

        list quality-of-service-profile {
        when " /ipi-qos:qos/ipi-qos:global/ipi-qos:map-profile/ipi-qos:cos-to-queue-profiles/ipi-qos:cos-to-queue-profile/ipi-qos:name  or /ipi-qos:qos/ipi-qos:global/ipi-qos:map-profile/ipi-qos:queue-color-to-cos-profiles/ipi-qos:queue-color-to-cos-profile/ipi-qos:name ";
            if-feature feature-list:HAVE_QOS;
            key "profile-type profile-name";
            description
                "Configuration VPLS QOS profile on AC";
            leaf profile-type  {
                type  leafref {
                    path  "../config/profile-type";
                }
                description "Specify map profile type for VPLS";
            } // END of profile-type definition.

            leaf profile-name  {
                type  leafref {
                    path  "../config/profile-name";
                }
                description "Specify profile name for map profile";
            } // END of profile-name definition.

            container config {
                description
                    "Configuration data for Attachment-Circuit";
                uses vpls-quality-of-service-config;
            } // END of config-container definition.
            container state {
                config false;
                description
                    "Operation state data for Attachment-Circuit";
                uses vpls-quality-of-service-config;
            } // END of state-container definition.
        } // End of quality-of-service-profile-list
    } // END of virtual-circuit-quality-of-service-top definition.
    grouping vpls-quality-of-service-config {
        description
            "Grouping for       VPLS QOS Profile Configuration attributes";
        leaf profile-type  {
            type  ipi-vpls-types:vpls_qos_map_profile_type_t;
            description "Specify map profile type for VPLS";
        } // END of profile-type definition.

        leaf profile-name  {
            type  string {
                length "1..1965";
                pattern "[^?' =,>|]+";
            }
            description "Specify profile name for map profile";
        } // END of profile-name definition.

    } // END of vpls-quality-of-service-config definition.
    grouping vpls-mac-learning-table-state {
        description
            "Top level grouping for Mac Learning table";
        leaf mac-address  {
            type  cml-data-types:cml_mac_addr_t {
                length "1..1965";
            }
            description "Attribute to acquire mac-address learnt on VPLS instance";
        } // END of mac-address definition.

        leaf vpls-identifier  {
            type  uint32;
            description "Attribute to acquire vpls-id for a VPLS instance";
        } // END of vpls-identifier definition.

        leaf learning-source-interface  {
            type  string {
                length "1..1965";
                pattern "[^?' =,>|]+";
            }
            description "Attribute to acquire interface name from where mac-address is learnt
                        on VPLS instance";
        } // END of learning-source-interface definition.

        leaf matched-vlan  {
            type  uint16;
            description "Attribute to acquire matched vlan value for the mac-address learnt";
        } // END of matched-vlan definition.

        leaf peer-address  {
            type  inet:ipv4-address;
            description "Attribute to acquire mesh peer address from whom mac-address is learnt";
        } // END of peer-address definition.

        leaf ageing-timeout  {
            type  uint32;
            units "seconds";
            description "Attribute to acquire ageing timeout for the learnt mac-address in VPLS
                        instance";
        } // END of ageing-timeout definition.

    } // END of vpls-mac-learning-table-state definition.
    grouping vpls-mac-learning-table-top {
        description
            "Top level grouping for Mac Learning table";

        list mac-learning-table {
            key "mac-address";
            config false;
            description
                "";
            leaf mac-address  {
                type  leafref {
                    path  "../state/mac-address";
                }
                description "";
            } // END of mac-address definition.

            container state {
                config false;
                description
                    "Operational state data";
                uses vpls-mac-learning-table-state;
            } // END of state-container definition.
        } // End of mac-learning-table-list
    } // END of vpls-mac-learning-table-top definition.
    grouping vpls-peer-list-state {
        description
            "Top level grouping for Operational Peer list";
        leaf peer-address  {
            type  inet:ipv4-address;
            description "Attribute to acquire destination peer address of a VPLS pseudowire";
        } // END of peer-address definition.

        leaf vpls-identifier  {
            type  uint32;
            description "Attribute to acquire vpls-id for a VPLS instance";
        } // END of vpls-identifier definition.

        leaf tunnel-label  {
            type  uint32;
            description "Attribute to acquire tunnel-label to be used for VPLS pseudowire";
        } // END of tunnel-label definition.

        leaf pseudowire-in-label  {
            type  uint32;
            description "Attribute to acquire incoming VC label for VPLS pseudowire";
        } // END of pseudowire-in-label definition.

        leaf pseudowire-out-label  {
            type  uint32;
            description "Attribute to acquire outgoing VC label for VPLS pseudowire";
        } // END of pseudowire-out-label definition.

        leaf peer-state  {
            type  ipi-vpls-types:vpls_peer_state_t;
            description "Attribute to acquire state of mesh peer pseudowire";
        } // END of peer-state definition.

        leaf pseudowire-status  {
            type  ipi-vpls-types:vpls_pseudowire_status_t;
            description "Attribute to acquire pseudowire status of a VPLS instance";
        } // END of pseudowire-status definition.

        leaf network-interface  {
            type  string {
                length "1..1965";
                pattern "[^?' =,>|]+";
            }
            description "Attribute to acquire the network interface name using which
                        mesh-pseudowire is created";
        } // END of network-interface definition.

        leaf signaling-protocol  {
            type  ipi-vpls-types:vpls_signaling_type_t;
            default "NA";
            description "Attribute to acquire the signaling protocol used for establishment of
                        vpls pseudowire";
        } // END of signaling-protocol definition.

    } // END of vpls-peer-list-state definition.
    grouping vpls-peer-list-top {
        description
            "Top level grouping for Operational Peer list";

        list peer-list {
            key "peer-address";
            config false;
            description
                "";
            leaf peer-address  {
                type  leafref {
                    path  "../state/peer-address";
                }
                description "";
            } // END of peer-address definition.

            container state {
                config false;
                description
                    "Operational state data";
                uses vpls-peer-list-state;
            } // END of state-container definition.
        } // End of peer-list-list
    } // END of vpls-peer-list-top definition.
    grouping vpls-quality-of-service-top {
        description
            "Top level grouping for VPLS QOS Profile on AC";

        list quality-of-service-profile {
        when " /ipi-qos:qos/ipi-qos:global/ipi-qos:map-profile/ipi-qos:cos-to-queue-profiles/ipi-qos:cos-to-queue-profile/ipi-qos:name  or /ipi-qos:qos/ipi-qos:global/ipi-qos:map-profile/ipi-qos:queue-color-to-cos-profiles/ipi-qos:queue-color-to-cos-profile/ipi-qos:name ";
            if-feature feature-list:HAVE_QOS;
            key "profile-type profile-name";
            description
                "Configuration VPLS QOS profile on AC";
            leaf profile-type  {
                type  leafref {
                    path  "../config/profile-type";
                }
                description "Specify map profile type for VPLS";
            } // END of profile-type definition.

            leaf profile-name  {
                type  leafref {
                    path  "../config/profile-name";
                }
                description "Specify profile name";
            } // END of profile-name definition.

            container config {
                description
                    "Configuration data for Attachment-Circuit";
                uses vpls-quality-of-service-config;
            } // END of config-container definition.
            container state {
                config false;
                description
                    "Operation state data for Attachment-Circuit";
                uses vpls-quality-of-service-config;
            } // END of state-container definition.
        } // End of quality-of-service-profile-list
    } // END of vpls-quality-of-service-top definition.
    grouping vpls-static-vpls-top {
        description
            "Top level Grouping for Static Forwarding for VPLS";

        list static-vpls {
        when " /ipi-network-instance:network-instances/ipi-network-instance:network-instance/ipi-l2vpn-vpls:vpls-instance/ipi-l2vpn-vpls:vpls-peers/ipi-l2vpn-vpls:vpls-peer/ipi-l2vpn-vpls:config/ipi-l2vpn-vpls:peer-type = '1' ";
            key "vpls-identifier peer-address";
            description
                "List for Static VPLS Forwarding Information Base";
            leaf vpls-identifier  {
                type  leafref {
                    path  "../config/vpls-identifier";
                }
                description "VPLS Instance Identifier for static VPLS signaling";
            } // END of vpls-identifier definition.

            leaf peer-address  {
                type  leafref {
                    path  "../config/peer-address";
                }
                description "Specify VPLS peer IPv4 address";
            } // END of peer-address definition.

            container config {
                description
                    "Configuration data for Static VPLS";
                uses vpls-static-forwarding-config;
                uses vpls-static-forwarding-keys-config;
            } // END of config-container definition.
            container state {
                config false;
                description
                    "Operation state data for Static VPLS";
                uses vpls-static-forwarding-config;
                uses vpls-static-forwarding-keys-config;
            } // END of state-container definition.
        } // End of static-vpls-list
    } // END of vpls-static-vpls-top definition.
    grouping vpls-static-hvpls-top {
        description
            "Top level Grouping for Static Forwarding for HVPLS";

        list static-hierarchical-vpls {
        when " /ipi-network-instance:network-instances/ipi-network-instance:network-instance/ipi-l2vpn-vpls:vpls-instance/ipi-l2vpn-vpls:vpls-peers/ipi-l2vpn-vpls:vpls-peer/ipi-l2vpn-vpls:config/ipi-l2vpn-vpls:peer-type = '1' ";
            key "vpls-identifier spoke-pseudowire-name";
            description
                "List for Configuration data of Static Forwarding for HVPLS";
            leaf vpls-identifier  {
                type  leafref {
                    path  "../config/vpls-identifier";
                }
                description "Specify VPLS identifier";
            } // END of vpls-identifier definition.

            leaf spoke-pseudowire-name  {
                type  leafref {
                    path  "../config/spoke-pseudowire-name";
                }
                description "Specify spoke virtual circuit name";
            } // END of spoke-pseudowire-name definition.

            container config {
                description
                    "Configuration data for Static HVPLS";
                uses vpls-static-forwarding-config;
                uses vpls-static-forwarding-hvpls-keys-config;
            } // END of config-container definition.
            container state {
                config false;
                description
                    "Operation state data for Static HVPLS";
                uses vpls-static-forwarding-config;
                uses vpls-static-forwarding-hvpls-keys-config;
            } // END of state-container definition.
        } // End of static-hierarchical-vpls-list
    } // END of vpls-static-hvpls-top definition.
    grouping vpls-static-forwarding-keys-config {
        description
            "Grouping for VPLS static forwarding configuration attributes";
        leaf vpls-identifier  {
            type  leafref {
                path  "/ipi-network-instance:network-instances/ipi-network-instance:network-instance/vpls-instance/config/vpls-identifier";
            }
            description "VPLS Instance Identifier for static VPLS signaling";
        } // END of vpls-identifier definition.

        leaf peer-address  {
            type  leafref {
                path  "/ipi-network-instance:network-instances/ipi-network-instance:network-instance/vpls-instance/vpls-peers/vpls-peer/config/peer-address";
            }
            description "Specify VPLS peer IPv4 address";
        } // END of peer-address definition.

    } // END of vpls-static-forwarding-keys-config definition.
    grouping vpls-static-forwarding-hvpls-keys-config {
        description
            "Grouping for VPLS static forwarding configuration attributes";
        leaf vpls-identifier  {
            type  leafref {
                path  "/ipi-network-instance:network-instances/ipi-network-instance:network-instance/vpls-instance/config/vpls-identifier";
            }
            description "Specify VPLS identifier";
        } // END of vpls-identifier definition.

        leaf spoke-pseudowire-name  {
            type  leafref {
                path  "/ipi-network-instance:network-instances/ipi-network-instance:network-instance/vpls-instance/spoke-pseudowire/config/pseudowire-name";
            }
            description "Specify spoke virtual circuit name";
        } // END of spoke-pseudowire-name definition.

    } // END of vpls-static-forwarding-hvpls-keys-config definition.
    grouping vpls-static-forwarding-config {
        description
            "Grouping for VPLS static forwarding configuration attributes";
        leaf in-label  {
            type  uint32 {
                 range "16..15999"  {
                    description "16..15999:In-coming Label";
                 }
            }
            mandatory true;
            description "Specify in-coming label for VPLS static forwarding";
        } // END of in-label definition.

        leaf out-label  {
            type  uint32 {
                 range "16..15999"  {
                    description "16..15999:Out-going Label <16-15999>";
                 }
            }
            mandatory true;
            description "Specify out going label for VPLS static forwarding";
        } // END of out-label definition.

        leaf out-interface-name  {
            type  string {
                length "1..1965";
                pattern "[^?' =,>|]+";
            }
            mandatory true;
            description "Specify provider facing interface name";
        } // END of out-interface-name definition.

    } // END of vpls-static-forwarding-config definition.
    grouping vpls-instance-global-state {
        description
            "Grouping for VPLS Instance global runtime attributes";
        leaf signaling-protocol  {
            type  ipi-vpls-types:vpls_signaling_type_t;
            default "NA";
            description "This attribute acquires signaling protocol used to establish VPLS
                        service";
        } // END of signaling-protocol definition.

        leaf route-distinguisher  {
            type  string {
                length "1..1965";
                pattern "[^?' =,>|]+";
            }
            description "This attribute acquires the RD value if signaling-protocol is BGP";
        } // END of route-distinguisher definition.

        leaf route-target  {
            type  string {
                length "1..1965";
                pattern "[^?' =,>|]+";
            }
            description "This attribute acquires RT value if signaling-protocol is BGP";
        } // END of route-target definition.

        leaf vpls-edge-id  {
            type  uint32;
            description "This attribute acquires ve-id value if signaling-protocol is BGP";
        } // END of vpls-edge-id definition.

        leaf attachment-circuit-status  {
            type  ipi-vpls-types:vpls_ac_status_t;
            description "This attribute acquires AC status which is mapped to VPLS instance";
        } // END of attachment-circuit-status definition.

        leaf vpls-type  {
            type  ipi-vpls-types:vpls_vc_type_t;
            description "This attribute acquires VPLS type as ethernet or vlan";
        } // END of vpls-type definition.

        leaf service-vlan-id  {
            type  uint16;
            description "This attribute acquires service vlan identifier value";
        } // END of service-vlan-id definition.

        leaf group-identifier  {
            type  uint32;
            description "This attribute acquires group identifier for pseudowire";
        } // END of group-identifier definition.

        leaf total-mac-addresses-learnt  {
            type  uint32;
            description "This attribute acquires the total number of mac-addresses learnt by
                        this VPLS Instance";
        } // END of total-mac-addresses-learnt definition.

    } // END of vpls-instance-global-state definition.
    grouping vpls-instance-global-config {
        description
            "Grouping for VPLS Instance global configuration  attributes";
        leaf vpls-identifier  {
            type  uint32 {
                 range "1..4294967295"  {
                    description "1..4294967295:Identifying value for VPLS";
                 }
            }
            mandatory true;
            description "Specify VPLS identifier";
        } // END of vpls-identifier definition.

        leaf service-transport-identifier  {
            type  ipi-vpls-types:vpls_svc_tpid_t;
            description "Specify service transport identifier";
        } // END of service-transport-identifier definition.

        leaf maximum-transmission-unit  {
            type  uint16 {
                 range "576..65535"  {
                    description "576..65535:Identifying value for VPLS";
                 }
            }
            default "1500";
            description "Set the Maximum Transmission Unit (MTU) size for a given VPLS
                        instance. This size is signaled to peer VPLS routers";
        } // END of maximum-transmission-unit definition.

        leaf vpls-description  {
            type  cml-data-types:cml_line_t {
                length "1..64";
            }
            default "NULL";
            description "Specify a description for this VPLS instance";
        } // END of vpls-description definition.

        leaf control-word  {
            type  empty;
            description "Control Word for VPLS instance";
        } // END of control-word definition.

        leaf mac-learning-disable  {
            type  empty;
            description "Specify mac learning disable for VPLS instance";
        } // END of mac-learning-disable definition.

        leaf mac-learning-limit  {
            if-feature feature-list:NOT_HAVE_TRIDENT2;
            if-feature feature-list:NOT_HAVE_TRIDENT2PLUS;
            type  uint32 {
                 range "5..32767"  {
                    description "5..32767:Mac learning limit value";
                 }
            }
            default "32767";
            description "Specify mac learning limit";
        } // END of mac-learning-limit definition.

        leaf attachment-circuit-group-name  {
            type  leafref {
                path  "/ipi-mpls:mpls/ipi-mpls:l2vpn/ipi-mpls:access-circuit-group/ipi-mpls:config/ipi-mpls:group-name";
            }
            description "Specify ac-group name";
        } // END of attachment-circuit-group-name definition.

    } // END of vpls-instance-global-config definition.
    grouping vpls-spoke-pseudowire-top {
        description
            "Top level grouping for H-VPLS spoke-pseudowire";

        list spoke-pseudowire {
            key "pseudowire-name";
            description
                "Spoke Pseudowire list for H-VPLS";
            leaf pseudowire-name  {
                type  leafref {
                    path  "../config/pseudowire-name";
                }
                description "Specify pseudowire name to be added";
            } // END of pseudowire-name definition.

            container config {
                description
                    "Configuration data for spoke-pseudowire";
                uses vpls-spoke-pseudowire-config;
            } // END of config-container definition.
            container state {
                config false;
                description
                    "Operation state data for spoke-pseudowire";
                uses vpls-spoke-pseudowire-config;
            } // END of state-container definition.
        } // End of spoke-pseudowire-list
    } // END of vpls-spoke-pseudowire-top definition.
    grouping vpls-spoke-pseudowire-config {
        description
            "Grouping for H-VPLS spoke-pseudowire configuration attributes";
        leaf pseudowire-name  {
            type  string {
                length "1..1965";
                pattern "[^?' =,>|]+";
            }
            description "Specify pseudowire name to be added";
        } // END of pseudowire-name definition.

        leaf pseudowire-type  {
            type  ipi-vpls-types:vpls_vc_spoke_type_t;
            default "ethernet";
            description "Specify pseudowire type";
        } // END of pseudowire-type definition.

    } // END of vpls-spoke-pseudowire-config definition.
    grouping vpls-peer-top {
        description
            "Top level grouping for VPLS Peer";
        container vpls-peers {
            description
                "Top level container for vpls peer";

            list vpls-peer {
            when " /ipi-network-instance:network-instances/ipi-network-instance:network-instance/ipi-l2vpn-vpls:vpls-instance/ipi-l2vpn-vpls:vpls-peers/ipi-l2vpn-vpls:vpls-peer/ipi-l2vpn-vpls:config/ipi-l2vpn-vpls:peer-type = '1'  or /ipi-network-instance:network-instances/ipi-network-instance:network-instance/ipi-l2vpn-vpls:vpls-instance/ipi-l2vpn-vpls:vpls-peers/ipi-l2vpn-vpls:config ";
                key "peer-address";
                description
                    "Configuration data for VPLS peer";
                leaf peer-address  {
                    type  leafref {
                        path  "../config/peer-address";
                    }
                    description "Specify VPLS peer address";
                } // END of peer-address definition.

                container config {
                    description
                        "Configuration data for vpls peer";
                    uses vpls-peer-config;
                } // END of config-container definition.
                container state {
                    config false;
                    description
                        "Operation state data for vpls peer";
                    uses vpls-peer-config;
                } // END of state-container definition.
                uses vpls-peer-fec129-top;
            } // End of vpls-peer-list
            container config {
                presence "Enable Ldp signaling for VPLS";
                description
                    "Global Configuration data for vpls peers";
                uses vpls-global-peer-config;
            } // END of config-container definition.
            container state {
                config false;
                description
                    "Global Operation state data for vpls peers";
                uses vpls-global-peer-config;
            } // END of state-container definition.
        } // END of vpls-peers-container definition.
    } // END of vpls-peer-top definition.
    grouping vpls-global-peer-config {
        description
            "Grouping for global vpls peer configuration attributes";
        leaf signaling-protocol-ldp  {
            when " /ipi-network-instance:network-instances/ipi-network-instance:network-instance/ipi-l2vpn-vpls:vpls-instance/ipi-l2vpn-vpls:vpls-peers/ipi-l2vpn-vpls:vpls-peer/ipi-l2vpn-vpls:config/ipi-l2vpn-vpls:peer-type != '1'  + not(/ipi-network-instance:network-instances/ipi-network-instance:network-instance/ipi-l2vpn-vpls:vpls-instance/ipi-l2vpn-vpls:bgp-signaling/ipi-l2vpn-vpls:config/ipi-l2vpn-vpls:signaling-protocol-bgp) + /ipi-network-instance:network-instances/ipi-network-instance:network-instance/ipi-l2vpn-vpls:vpls-instance/ipi-l2vpn-vpls:vpls-peers/ipi-l2vpn-vpls:vpls-peer/ipi-l2vpn-vpls:config/ipi-l2vpn-vpls:peer-type != '1' ";
            type  empty;
            mandatory true;
            description "Specify protocol used for signaling is ldp";
        } // END of signaling-protocol-ldp definition.

        leaf disable-mac-withdrawal  {
            when " /ipi-network-instance:network-instances/ipi-network-instance:network-instance/ipi-l2vpn-vpls:vpls-instance/ipi-l2vpn-vpls:vpls-peers/ipi-l2vpn-vpls:config/ipi-l2vpn-vpls:signaling-protocol-ldp ";
            type  empty;
            description "Specify mac address withdrawal disable";
        } // END of disable-mac-withdrawal definition.

        leaf vpls-encapsulation-type  {
            type  ipi-vpls-types:vpls_vc_type_t;
            description "Specify encapsulation type";
        } // END of vpls-encapsulation-type definition.

    } // END of vpls-global-peer-config definition.
    grouping vpls-peer-config {
        description
            "Grouping for vpls peer configuration attributes";
        leaf peer-address  {
            type  inet:ipv4-address;
            description "Specify VPLS peer address";
        } // END of peer-address definition.

        leaf tunnel-name  {
            when " not(../tunnel-identifier) + not(../tunnel-policy) ";
            type  string {
                length "1..128";
                pattern "[^?' =,>|]+";
            }
            description "Specify tunnel name";
        } // END of tunnel-name definition.

        leaf tunnel-policy  {
            when " not(../tunnel-identifier) + not(../tunnel-name) ";
            if-feature feature-list:HAVE_MPLS_SERVICE_MAPPING;
            type  string {
                length "1..127";
                pattern "[^?' =,>|]+";
            }
            description "Specify tunnel selection policy name";
        } // END of tunnel-policy definition.

        leaf tunnel-identifier  {
            when " not(../tunnel-name) + not(../tunnel-policy) ";
            type  uint32 {
                 range "1..5000"  {
                    description "1..5000:Identifying value for Tunnel-id";
                 }
            }
            description "Specify static tunnel identifier value";
        } // END of tunnel-identifier definition.

        leaf peer-type  {
            when " not(/ipi-network-instance:network-instances/ipi-network-instance:network-instance/ipi-l2vpn-vpls:vpls-instance/ipi-l2vpn-vpls:vpls-peers/ipi-l2vpn-vpls:config/ipi-l2vpn-vpls:signaling-protocol-ldp ) + not(/ipi-network-instance:network-instances/ipi-network-instance:network-instance/ipi-l2vpn-vpls:vpls-instance/ipi-l2vpn-vpls:bgp-signaling/ipi-l2vpn-vpls:config/ipi-l2vpn-vpls:signaling-protocol-bgp) + not(/ipi-network-instance:network-instances/ipi-network-instance:network-instance/ipi-l2vpn-vpls:vpls-instance/ipi-l2vpn-vpls:vpls-peers/ipi-l2vpn-vpls:config/ipi-l2vpn-vpls:signaling-protocol-ldp) ";
            type  ipi-vpls-types:vpls_peer_type_t;
            default "manual";
            description "Specify that peer type is manual and  no signaling is used to set-up
                        the Virtual Circuit";
        } // END of peer-type definition.

    } // END of vpls-peer-config definition.
    grouping vpls-peer-fec129-top {
        description
            "Top level grouping for Fec129 (Genfec) VPLS Peer";

        list fec129 {
        when " /ipi-network-instance:network-instances/ipi-network-instance:network-instance/ipi-l2vpn-vpls:vpls-instance/ipi-l2vpn-vpls:vpls-peers/ipi-l2vpn-vpls:config/ipi-l2vpn-vpls:signaling-protocol-ldp ";
            key "attachment-group-identifier source-attachment-individual-identifier target-attachment-individual-identifier";
            max-elements 1;
            description
                "Configuration data for VPLS genfec peer";
            leaf attachment-group-identifier  {
                type  leafref {
                    path  "../config/attachment-group-identifier";
                }
                description "Specify the Address Group Identifier";
            } // END of attachment-group-identifier definition.

            leaf source-attachment-individual-identifier  {
                type  leafref {
                    path  "../config/source-attachment-individual-identifier";
                }
                description "Specify the Source Attachment Individual Identifier";
            } // END of source-attachment-individual-identifier definition.

            leaf target-attachment-individual-identifier  {
                type  leafref {
                    path  "../config/target-attachment-individual-identifier";
                }
                description "Specify the Target Attachment Individual Identifier";
            } // END of target-attachment-individual-identifier definition.

            container config {
                description
                    "Configuration data for vpls peer";
                uses vpls-peer-fec129-config;
            } // END of config-container definition.
            container state {
                config false;
                description
                    "Operation state data for vpls peer";
                uses vpls-peer-fec129-config;
            } // END of state-container definition.
        } // End of fec129-list
    } // END of vpls-peer-fec129-top definition.
    grouping vpls-peer-fec129-config {
        description
            "Configuration attributes for genfec based VPLS peer";
        leaf attachment-group-identifier  {
            type  string {
                length "1..1965";
                pattern "[^?' =,>|]+";
            }
            description "Specify the Address Group Identifier";
        } // END of attachment-group-identifier definition.

        leaf source-attachment-individual-identifier  {
            type  string {
                length "1..1965";
                pattern "[^?' =,>|]+";
            }
            description "Specify the Source Attachment Individual Identifier";
        } // END of source-attachment-individual-identifier definition.

        leaf target-attachment-individual-identifier  {
            type  string {
                length "1..1965";
                pattern "[^?' =,>|]+";
            }
            description "Specify the Target Attachment Individual Identifier";
        } // END of target-attachment-individual-identifier definition.

        leaf tunnel-name  {
            when " not(/ipi-network-instance:network-instances/ipi-network-instance:network-instance/ipi-l2vpn-vpls:vpls-instance/ipi-l2vpn-vpls:vpls-peers/ipi-l2vpn-vpls:config/ipi-l2vpn-vpls:signaling-protocol-ldp) ";
            type  string {
                length "1..1965";
                pattern "[^?' =,>|]+";
            }
            description "Specify tunnel id value";
        } // END of tunnel-name definition.

        leaf tunnel-policy  {
            when " not(/ipi-network-instance:network-instances/ipi-network-instance:network-instance/ipi-l2vpn-vpls:vpls-instance/ipi-l2vpn-vpls:vpls-peers/ipi-l2vpn-vpls:config/ipi-l2vpn-vpls:signaling-protocol-ldp) ";
            if-feature feature-list:HAVE_MPLS_SERVICE_MAPPING;
            type  string {
                length "1..127";
                pattern "[^?' =,>|]+";
            }
            description "Specify tunnel selection policy name";
        } // END of tunnel-policy definition.

        leaf tunnel-identifier  {
            type  string {
                length "1..1965";
                pattern "[^?' =,>|]+";
            }
            description "Specify tunnel id value";
        } // END of tunnel-identifier definition.

    } // END of vpls-peer-fec129-config definition.
    grouping vpls-bgp-top {
        description
            "Top level grouping for BGP VPLS";
        container bgp-signaling {
            if-feature feature-list:HAVE_BGP_VPLS;
            description
                "Top level container for BGP vpls";
            container config {
                when " /ipi-network-instance:network-instances/ipi-network-instance:network-instance/ipi-l2vpn-vpls:vpls-instance/ipi-l2vpn-vpls:vpls-peers/ipi-l2vpn-vpls:vpls-peer/ipi-l2vpn-vpls:config/ipi-l2vpn-vpls:peer-type != '1'  + not(/ipi-network-instance:network-instances/ipi-network-instance:network-instance/ipi-l2vpn-vpls:vpls-instance/ipi-l2vpn-vpls:vpls-peers/ipi-l2vpn-vpls:config/ipi-l2vpn-vpls:signaling-protocol-ldp) ";
                presence "Enable BGP VPLS";
                description
                    "Configuration data for bgp vpls";
                uses vpls-bgp-config;
            } // END of config-container definition.
            container state {
                config false;
                description
                    "Operation state data for bgp vpls";
                uses vpls-bgp-config;
            } // END of state-container definition.
        } // END of bgp-signaling-container definition.
    } // END of vpls-bgp-top definition.
    grouping vpls-bgp-config {
        description
            "Grouping for BGP VPLS Configuration attributes";
        leaf signaling-protocol-bgp  {
            type  empty;
            mandatory true;
            description "Specify protocol used for signaling is bgp";
        } // END of signaling-protocol-bgp definition.

        leaf vpls-edge-identifier  {
            type  int32 {
                 range "1..1000"  {
                    description "1..1000:VE ID Range";
                 }
            }
            description "Specify VPLS edge identifier value";
        } // END of vpls-edge-identifier definition.

        leaf tunnel-policy  {
            if-feature feature-list:HAVE_MPLS_SERVICE_MAPPING;
            type  string {
                length "1..127";
                pattern "[^?' =,>|]+";
            }
            description "Specify tunnel selection policy name";
        } // END of tunnel-policy definition.

    } // END of vpls-bgp-config definition.
    grouping vpls-access-interface-counters-state {
        description
            "Top level grouping for access-interface-counters";
        leaf interface-name  {
            type  leafref {
                path  "/ipi-interface:interfaces/ipi-interface:interface/ipi-interface:name";
            }
            description "Attribute to acquire access interface name";
        } // END of interface-name definition.

        leaf vpls-identifier  {
            type  uint32;
            description "Attribute to acquire vpls-id for a VPLS instance";
        } // END of vpls-identifier definition.

        leaf service-template-name  {
            type  string {
                length "1..1965";
                pattern "[^?' =,>|]+";
            }
            description "Attribute to acquire Customer Service Template name mapped to this
                        vpls AC interface";
        } // END of service-template-name definition.

        leaf in-packets  {
            type  uint64;
            description "Attribute to acquire number of received(Rx) packets on this AC
                        interface";
        } // END of in-packets definition.

        leaf in-bytes  {
            type  uint64;
            description "Attribute to acquire number of received(Rx) bytes on this AC interface";
        } // END of in-bytes definition.

        leaf out-packets  {
            type  uint64;
            description "Attribute to acquire number of sent(Tx) packets on this AC interface";
        } // END of out-packets definition.

        leaf out-bytes  {
            type  uint64;
            description "Attribute to acquire number of sent(Tx) bytes on this AC interface";
        } // END of out-bytes definition.

    } // END of vpls-access-interface-counters-state definition.
    grouping vpls-network-interface-counters-state {
        description
            "Top level grouping for network-interface-counters";
        leaf peer-address  {
            type  inet:ipv4-address;
            description "Attribute to acquire peer-address for VPLS instance";
        } // END of peer-address definition.

        leaf vpls-identifier  {
            type  uint32;
            description "Attribute to acquire vpls-id for a VPLS instance";
        } // END of vpls-identifier definition.

        leaf peer-state  {
            type  ipi-vpls-types:vpls_peer_state_t;
            description "Attribute to acquire vpls-id for a VPLS instance";
        } // END of peer-state definition.

        leaf interface-name  {
            type  leafref {
                path  "/ipi-interface:interfaces/ipi-interface:interface/ipi-interface:name";
            }
            description "Attribute to acquire network interface name";
        } // END of interface-name definition.

        leaf in-packets  {
            type  uint64;
            description "Attribute to acquire number of received(Rx) packets on this AC
                        interface";
        } // END of in-packets definition.

        leaf in-bytes  {
            type  uint64;
            description "Attribute to acquire number of received(Rx) bytes on this AC interface";
        } // END of in-bytes definition.

        leaf out-packets  {
            type  uint64;
            description "Attribute to acquire number of sent(Tx) packets on this AC interface";
        } // END of out-packets definition.

        leaf out-bytes  {
            type  uint64;
            description "Attribute to acquire number of sent(Tx) bytes on this AC interface";
        } // END of out-bytes definition.

    } // END of vpls-network-interface-counters-state definition.
    grouping vpls-counters-top {
        description
            "Top level grouping for Counters";

        list access-interface-counters {
            if-feature feature-list:HAVE_MPLS_STATS;
            key "interface-name";
            config false;
            description
                "";
            leaf interface-name  {
                type  leafref {
                    path  "../state/interface-name";
                }
                description "";
            } // END of interface-name definition.

            container state {
                config false;
                description
                    "Operational state data";
                uses vpls-access-interface-counters-state;
            } // END of state-container definition.
        } // End of access-interface-counters-list

        list network-interface-counters {
            if-feature feature-list:HAVE_MPLS_STATS;
            key "peer-address";
            config false;
            description
                "";
            leaf peer-address  {
                type  leafref {
                    path  "../state/peer-address";
                }
                description "Attribute to acquire peer-address for VPLS instance";
            } // END of peer-address definition.

            container state {
                config false;
                description
                    "Operational state data";
                uses vpls-network-interface-counters-state;
            } // END of state-container definition.
        } // End of network-interface-counters-list
    } // END of vpls-counters-top definition.
    grouping vpls-interface-config {
        description
            "Grouping for Interface config attribute";
        leaf name  {
            type  leafref {
                path  "/ipi-interface:interfaces/ipi-interface:interface/ipi-interface:name";
            }
            description "This attribute describes the interface on which attachment circuit is
                        to be created for  pseudowire.";
        } // END of name definition.

    } // END of vpls-interface-config definition.
    grouping vpls-interface-top {
        description
            "Top level grouping for interface level configuration for PW";
        container interfaces {
            description
                "Top level container for interface level configuration for VPLS";

            list interface {
            when " /ipi-l2vpn-vpls:vpls/ipi-l2vpn-vpls:interfaces/ipi-l2vpn-vpls:interface/ipi-l2vpn-vpls:vpls-access/ipi-l2vpn-vpls:config/ipi-l2vpn-vpls:enable ";
                key "name";
                description
                    "VPLS interface related configuration";
                leaf name  {
                    type  leafref {
                        path  "../config/name";
                    }
                    description "This attribute describes the interface on which attachment circuit is
                                to be created for  pseudowire.";
                } // END of name definition.

                container config {
                    when " /ipi-l2vpn-vpls:vpls/ipi-l2vpn-vpls:interfaces/ipi-l2vpn-vpls:interface/ipi-l2vpn-vpls:vpls-access/ipi-l2vpn-vpls:config/ipi-l2vpn-vpls:enable ";
                    description
                        "Configuration container for interface list";
                    uses vpls-interface-config;
                } // END of config-container definition.
                container state {
                    config false;
                    description
                        "Operation container for interface list";
                    uses vpls-interface-config;
                } // END of state-container definition.
                uses l2vpn-vpls-top;
            } // End of interface-list
        } // END of interfaces-container definition.
    } // END of vpls-interface-top definition.
    grouping l2vpn-vpls-top {
        description
            "Top level grouping for L2VPN VPLS configuration";
        container vpls-access {
            if-feature feature-list:HAVE_SUBINTERFACE;
            description
                "Container for L2vpn Vpls data";
            container config {
                presence "yes";
                description
                    "Configuration data for L2VPN VPLS";
                uses l2vpn-vpls-config;
            } // END of config-container definition.
            container state {
                config false;
                description
                    "Operation state data for L2VPN VPLS";
                uses l2vpn-vpls-config;
            } // END of state-container definition.
        } // END of vpls-access-container definition.
    } // END of l2vpn-vpls-top definition.
    grouping l2vpn-vpls-config {
        description
            "Grouping for L2VPN VPLS variables for sub interfaces";
        leaf enable  {
            type  empty;
            mandatory true;
            description "This attribute is used to enable VPLS service on Subinterface";
        } // END of enable definition.

        leaf vpls-name  {
            type  string {
                length "1..30";
                pattern "[^?' =,>|]+";
            }
            description "This attribute uniquely identifies a VPLS service on Subinterface";
        } // END of vpls-name definition.

        leaf disable-mac-learning  {
            type  empty;
            description "Use this attribute to disable dynamic learning of MAC's";
        } // END of disable-mac-learning definition.

        leaf-list static-mac-address  {
            type  cml-data-types:cml_mac_addr_t {
                length "1..1965";
            }
            description "Specify static-mac to be added on L2VPN VPLS";
        } // END of static-mac-address definition.

    } // END of l2vpn-vpls-config definition.
    grouping vpls-global-counters-state {
        description
            "Grouping for global counters for VPLS";
        leaf total-instances  {
            type  yang:counter32;
            description "This attribute acquires total VPLS instances";
        } // END of total-instances definition.

        leaf active-instances  {
            type  yang:counter32;
            description "This attribute acquires total active VPLS instances";
        } // END of active-instances definition.

        leaf inactive-instances  {
            type  yang:counter32;
            description "This attribute acquires total non-active VPLS instances";
        } // END of inactive-instances definition.

    } // END of vpls-global-counters-state definition.
    grouping vpls-global-top {
        description
            "Top level grouping for global VPLS attributes";
        container global {
            description
                "Top level container for global configuration for VPLS";
            container state {
                config false;
                description
                    "State container for operational attributes";
                container counters {
                    config false;
                    description
                        "Operational container for VPLS counters";
                    uses vpls-global-counters-state;
                } // END of counters-container definition.
            } // END of state-container definition.
        } // END of global-container definition.
    } // END of vpls-global-top definition.

    grouping  vpls-grouping {
    description
        "VPLS global level container";
    container vpls {
        description
            "VPLS global level container";
        container attachment-circuit {
            description
                "VPLS-Attachment Circuit container";
            uses vpls-service-template-mapping-top;
        } // END of attachment-circuit-container definition.
        container static-forwarding {
            description
                "Static VPLS Forwarding Information Base container";
            uses vpls-static-vpls-top;
            uses vpls-static-hvpls-top;
        } // END of static-forwarding-container definition.
        uses vpls-interface-top;
        uses vpls-global-top;
    } // END of vpls-container definition.
    } // END of vpls-grouping definition.

    grouping  vpls-instance-grouping {
    description
        "Top level list for VPLS-Instance";
    container vpls-instance {
        description
            "Top level list for VPLS-Instance";
        container config {
            presence "Create VPLS Instance";
            description
                "Configuration data for VPLS-Instance";
            uses vpls-instance-global-config;
        } // END of config-container definition.
        container state {
            config false;
            description
                "Operation state data for VPLS-Instance";
            uses vpls-instance-global-config;
            uses vpls-instance-global-state;
        } // END of state-container definition.
        uses vpls-spoke-pseudowire-top;
        uses vpls-peer-top;
        uses vpls-bgp-top;
        uses vpls-quality-of-service-top;
        uses vpls-mac-learning-table-top;
        uses vpls-peer-list-top;
        uses vpls-counters-top;
    } // END of vpls-instance-container definition.
    } // END of vpls-instance-grouping definition.

    uses vpls-grouping;
    augment /ipi-network-instance:network-instances/ipi-network-instance:network-instance {
    when " /ipi-network-instance:network-instances/ipi-network-instance:network-instance/ipi-l2vpn-vpls:vpls-instance/ipi-l2vpn-vpls:config/ipi-l2vpn-vpls:vpls-identifier + /ipi-network-instance:network-instances/ipi-network-instance:network-instance/ipi-network-instance:instance-type = 'vpls' ";
        description
            "Top level list for VPLS-Instance";
        uses vpls-instance-grouping;
    }


    rpc clear-mpls-vpls-name-statistics-port-type {
        description "Use this attribute to clear mpls vpls statistics by portType";
        input  {
            leaf port-type  {
                type ipi-vpls-types:vpls_port_type_t;
                mandatory true;
                description "Specify port type";
            }
            leaf port-circuit-name  {
                type string;
                mandatory true;
                description "Specify port circuit name";
            }
        }
    }

    rpc clear-mpls-vpls-name-statistics-network-port-peer {
        description "Use this attribute to clear mpls vpls statistics by network portType";
        input  {
            leaf port-circuit-name  {
                type string;
                mandatory true;
                description "Specify port circuit name";
            }
            leaf vc-circuit-type  {
                type ipi-vpls-types:vpls_peer_address_type_t;
                mandatory true;
                description "Specify peer VC circuit name";
            }
        }
    }

    rpc clear-mpls-vpls-name-statistics-network-port-spoke {
        description "Use this attribute to clear mpls vpls statistics by network portType";
        input  {
            leaf port-circuit-name  {
                type string;
                mandatory true;
                description "Specify port circuit name";
            }
            leaf vc-circuit-type  {
                type ipi-vpls-types:vpls_spoke_vc_type_t;
                mandatory true;
                description "Specify VC circuit name";
            }
        }
    }

    rpc clear-mpls-vpls-name-statistics-access-port {
        description "Use this attribute to clear mpls l2-circuit statistics by access
                    portType";
        input  {
            leaf port-circuit-name  {
                type string;
                mandatory true;
                description "Specify port circuit name";
            }
            leaf vc-interface-name  {
                type string;
                mandatory true;
                description "Specify ingress VC interface name";
            }
            leaf vc-access-type  {
                type ipi-vpls-types:vpls_mpls_access_type_t;
                mandatory true;
                description "Specify VC access type";
            }
        }
    }

    rpc clear-mpls-vpls-name-statistics {
        description "Use this attribute to clear vpls statistics";
        input  {
            leaf vpls-circuit-name  {
                type string;
                mandatory true;
                description "Specify VC circuit name";
            }
        }
    }

    rpc clear-mpls-vpls-mac-addresses-for-instance {
        description "Use this attribute to clear mpls vpls by NAME and mac_addresses";
        input  {
            leaf name  {
                type string;
                mandatory true;
                description "Specify VPLS instance name";
            }
        }
    }

    rpc clear-mpls-vpls-mac-addresses-all {
        description "Use this attribute to clear mpls vpls mac_addresses";
    }

}

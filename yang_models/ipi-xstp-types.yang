/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-xstp-types.yang
*
*/

module ipi-xstp-types {

    yang-version 1.1;

    namespace   "http://www.ipinfusion.com/yang/ocnos/ipi-xstp-types";

    prefix "ipi-xstp-types";

    organization
        "IP Infusion Inc.";

    contact
        "Address: 3965 Freedom Circle, Suite 200, Santa Clara, CA 95054
         Phone: +1 408-400-1900
         E-mail: support@ipinfusion.com
         Web: http://www.ipinfusion.com/";

    description
        "MSTP Types";


    revision "2021-12-01" {
        description "Added XSTP operational data types";
        reference " 0.3.0.";
    }

    revision "2021-09-03" {
        description "Update descriptions of attribute";
        reference " 0.2.0.";
    }

    revision "2021-07-01" {
        description "Initial Version";
        reference " 0.1.0.";
    }



    typedef  xstp_bridge_forward_t {
        type enumeration {
            enum bridge-blocked {
                value 0;
                description "put all ports of the bridge into blocked state";
            }
            enum bridge-forward {
                value 1;
                description "put all ports of the bridge into forwarding state";
            }
        }
        description "type definition for XSTP_BRIDGE_FORWARD_T";
    }

    typedef  xstp_bridge_type_t {
        type enumeration {
            enum spanning-tree {
                value 1;
                description "IEEE 801.1Q spanning-tree protocol";
            }
            enum rapid-spanning-tree {
                value 3;
                description "IEEE 801.1w rapid spanning-tree protocol";
            }
            enum multiple-spanning-tree {
                value 5;
                description "IEEE 802.1s multiple spanning-tree protocol";
            }
        }
        description "type definition for XSTP_BRIDGE_TYPE_T";
    }

    typedef  xstp_path_cost_method_t {
        type enumeration {
            enum short {
                value 0;
                description "short - Use 16 bit based values for default port path cost";
            }
            enum long {
                value 1;
                description "long  - Use 32 bit based values for default port path costs";
            }
            enum default {
                value 2;
                description "Default";
            }
        }
        description "type definition for XSTP_PATH_COST_METHOD_T";
    }

    typedef  mstp_instance_type_t {
        type enumeration {
            enum instance-spbm {
                value 4092;
                description "instance,spbm instance";
            }
            enum instance-spbv {
                value 4093;
                description "instance,spbv instance";
            }
        }
        description "type definition for MSTP_INSTANCE_TYPE_T";
    }

    typedef  mstp_range_t {
        type uint16 {
             range 1..63;
        }
        description "type definition for MSTP_RANGE_T";
    }

    typedef  mstp_instance_t {
        type union {
            type mstp_instance_type_t {

            }
            type mstp_range_t {

            }
        }
        description "type definition for MSTP_INSTANCE_T";
    }

    typedef  xstp_port_edge_t {
        type enumeration {
            enum edgeport {
                value 0;
                description "edgeport - enable it as edgeport";
            }
            enum portfast {
                value 1;
                description "portfast - enable fast transitions";
            }
        }
        description "type definition for XSTP_PORT_EDGE_T";
    }

    typedef  xstp_bpdu_t {
        type enumeration {
            enum enable {
                value 0;
                description "Enable";
            }
            enum disable {
                value 1;
                description "Disable";
            }
            enum default {
                value 2;
                description "Default";
            }
        }
        description "type definition for XSTP_BPDU_T";
    }

    typedef  xstp_link_type_t {
        type enumeration {
            enum shared {
                value 0;
                description "shared - disable rapid transition";
            }
            enum point-to-point {
                value 1;
                description "point-to-point - enable rapid transition";
            }
            enum auto {
                value 2;
                description "auto - will be set to either p2p or shared based on duplex state";
            }
        }
        description "type definition for XSTP_LINK_TYPE_T";
    }

    typedef  mstp_port_role_t {
        type enumeration {
            enum Masterport {
                value 0;
                description "Masterport";
            }
            enum Alternate {
                value 1;
                description "Alternate";
            }
            enum Rootport {
                value 2;
                description "Rootport";
            }
            enum Designated {
                value 3;
                description "Designated";
            }
            enum Disabled {
                value 4;
                description "Disabled";
            }
            enum Backup {
                value 5;
                description "Backup";
            }
        }
        description "type definition for MSTP_PORT_ROLE_T";
    }

    typedef  mstp_port_state_t {
        type enumeration {
            enum Discarding {
                value 0;
                description "Discarding";
            }
            enum Listening {
                value 1;
                description "Listening";
            }
            enum Learning {
                value 2;
                description "Learning";
            }
            enum Forwarding {
                value 3;
                description "Forwarding";
            }
            enum Blocked {
                value 4;
                description "Blocked";
            }
            enum Error {
                value 5;
                description "Error";
            }
            enum root-inconsistent {
                value 6;
                description "root-inconsistent";
            }
        }
        description "type definition for MSTP_PORT_STATE_T";
    }

    typedef  mstp_instance_spbm_type_t {
        type union {
            type int32 {
                range "1..63";

            }
            type mstp_instance_spbm_t {

            }
        }
        description "type definition for MSTP_INSTANCE_SPBM_TYPE_T";
    }

    typedef  mstp_instance_spbm_t {
        type enumeration {
            enum spbm {
                value 4092;
                description "spbm instance";
            }
        }
        description "type definition for MSTP_INSTANCE_SPBM_T";
    }

    typedef  xstp_ageing_disable {
        type enumeration {
            enum 0 {
                value 0;
                description "Disable Ageing Time";
            }
        }
        description "type definition for XSTP_AGEING_DISABLE";
    }

    typedef  xstp_ageing_time_t {
        type union {
            type uint32 {
                range "10..572";

            }
            type xstp_ageing_disable {

            }
        }
        description "type definition for XSTP_AGEING_TIME_T";
    }

    typedef  mstp_debug_t {
        type bits {
            bit mstp-protocol {
                position 1;
                description "debug mstp,mstp protocol";
            }
            bit mstp-protocol-detail {
                position 2;
                description "debug mstp,mstp protocol,display detailed information";
            }
            bit mstp-timer {
                position 3;
                description "debug mstp,mstp timer";
            }
            bit mstp-timer-detail {
                position 4;
                description "debug mstp,mstp timer,display detailed information";
            }
            bit mstp-packet-tx {
                position 5;
                description "debug mstp,mstp packet,tx";
            }
            bit mstp-packet-rx {
                position 6;
                description "debug mstp,mstp packet,rx";
            }
            bit mstp-cli {
                position 7;
                description "debug mstp,mstp cli";
            }
            bit mstp-bpdu {
                position 8;
                description "debug mstp,mstp bpdu";
            }
            bit mstp-mcec {
                position 9;
                description "debug mstp,mstp mcec";
            }
        }
        description "type definition for MSTP_DEBUG_T";
    }

}

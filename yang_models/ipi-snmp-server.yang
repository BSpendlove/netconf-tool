/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-snmp-server.yang
*
*/

module ipi-snmp-server {

    yang-version 1.1;

    namespace   "http://www.ipinfusion.com/yang/ocnos/ipi-snmp-server";

    prefix "ipi-snmp-server";

    import ipi-snmp {
        prefix ipi-snmp;
        revision-date 2021-07-28;
    }

    import cml-data-types {
        prefix cml-data-types;
        revision-date 2022-04-04;
    }

    import ipi-network-instance {
        prefix ipi-network-instance;
        revision-date 2021-11-10;
    }

    import ipi-vrf {
        prefix ipi-vrf;
        revision-date 2021-09-03;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "This module provides Simple Network Management Protocol configuration";


    revision "2021-12-15" {
        description "Some if-features included in some dependent objects between this module and ipi-snmp-server-extended";
        reference " 0.2.1.";
    }

    revision "2021-11-16" {
        description "Module restructuring";
        reference " 0.2.0.";
    }

    revision "2018-06-21" {
        description "Initial Version";
        reference " 0.1.0.";
    }

    grouping snmp-server-global-config {
        description
            "SNMP server global configuration";
        leaf system-contact  {
            if-feature feature-list:HAVE_SNMP_AGENT;
            type  cml-data-types:cml_line_t {
                length "1..1965";
            }
            description "Use this attribute to set the system contact information for the
                        device (sysContact object)";
        } // END of system-contact definition.

        leaf system-location  {
            if-feature feature-list:HAVE_SNMP_AGENT;
            type  cml-data-types:cml_line_t {
                length "1..1965";
            }
            description "Use this attribute to set the physical location information of the
                        device (sysLocation object)";
        } // END of system-location definition.

        leaf tcp-session-enabled  {
            if-feature feature-list:HAVE_SNMP_AGENT;
            type  empty;
            description "Use this attribute to start the SNMP agent daemon over TCP";
        } // END of tcp-session-enabled definition.

    } // END of snmp-server-global-config definition.
    grouping snmp-server-global-top {
        description
            "SNMP server global configuration";
        container global {
            description
                "SNMP server global container configuration";
            container config {
                description
                    "Configuration data for SNMP server global configuration";
                uses snmp-server-global-config;
            } // END of config-container definition.
            container state {
                config false;
                description
                    "Operational state data for SNMP server global configuration";
                uses snmp-server-global-config;
            } // END of state-container definition.
        } // END of global-container definition.
    } // END of snmp-server-global-top definition.
    grouping snmp-server-config {
        description
            "SNMP server configuration";
        leaf vrf-name  {
            if-feature feature-list:HAVE_VRF;
            type  leafref {
                path  "/ipi-network-instance:network-instances/ipi-network-instance:network-instance/ipi-vrf:vrf/ipi-vrf:config/ipi-vrf:vrf-name";
            }
            description "VRF name associated with this instance.";
        } // END of vrf-name definition.

        leaf enabled  {
            type  boolean;
            description "Use this attribute to enable SNMP server";
        } // END of enabled definition.

    } // END of snmp-server-config definition.
    grouping snmp-server-top {
        description
            "SNMP server top configuration";

        list server {
            key "vrf-name";
            max-elements 1;
            description
                "Server list for SNMP configuration";
            leaf vrf-name  {
                type  leafref {
                    path  "../config/vrf-name";
                }
                description "VRF name associated with this instance.";
            } // END of vrf-name definition.

            container config {
                description
                    "Configuration data for SNMP Server";
                uses snmp-server-config;
            } // END of config-container definition.
            container state {
                config false;
                description
                    "Operational state data for SNMP Server";
                uses snmp-server-config;
            } // END of state-container definition.
            uses snmp-server-global-top;
        } // End of server-list
    } // END of snmp-server-top definition.

    grouping  servers-grouping {
    description
        "Container for SNMP servers configuration";
    container servers {
        description
            "Container for SNMP servers configuration";
        uses snmp-server-top;
    } // END of servers-container definition.
    } // END of servers-grouping definition.

    augment /ipi-snmp:snmp {
        if-feature feature-list:HAVE_SNMP_AGENT;
        description
            "Container for SNMP servers configuration";
        uses servers-grouping;
    }


}

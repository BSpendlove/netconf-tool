/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-customstats.yang
*
*/

module ipi-customstats {

    yang-version 1.1;

    namespace   "http://www.ipinfusion.com/yang/ocnos/ipi-customstats";

    prefix "ipi-customstats";

    import ietf-yang-types {
        prefix yang;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Custom Stats Managed Object";


    revision "2021-12-07" {
        description "Restructured module as per open-config";
        reference " 0.2.0.";
    }

    revision "2018-05-06" {
        description "Initial Version";
        reference " 0.1.0.";
    }



    notification platform-cpu-queue-full {

        description "Notification to send information when CPU queue is full..";

        // severity "CRITICAL";
        // eventClass "STATE";
        leaf queue-id {
            type  uint8;
        description
            "This is a unique number representing each queue in CPU";
        }

        leaf queue-name {
            type  string;
        description
            "Queue Name corresponding to the Queue Id.";
        }

        leaf rate-percent {
            type  int8;
        description
            "Percentage of control packets transmitted in the CPU queue.
                    Value of -1 indicates rate percentage is not applicable.";
        }

        leaf tx-pkt-rate {
            type  yang:counter32;
        description
            "The number of outbound packets transmitted from the corresponding CPU
                    queue.";
        }

        leaf last-increment-count {
            type  yang:counter64;
        description
            "The number of Last Dropped Pkts in the corresponding CPU queue.
                    This is Updated at every 5sec interval.";
        }

        leaf last-increment-time {
            type  yang:date-and-time;
        description
            "Last increment time of Tx Dropped Packets in CPU Queue.
                    This is Updated at every 5sec interval.";
        }
    }

    notification platform-cpu-queue-high {

        description "Notification to send information when CPU queue is high crossing threshold of 90%..";

        // severity "WARNING";
        // eventClass "STATE";
        leaf queue-id {
            type  uint8;
        description
            "This is a unique number representing each queue in CPU";
        }

        leaf queue-name {
            type  string;
        description
            "Queue Name corresponding to the Queue Id.";
        }

        leaf rate-percent {
            type  int8;
        description
            "Percentage of control packets transmitted in the CPU queue.
                    Value of -1 indicates rate percentage is not applicable.";
        }

        leaf tx-pkt-rate {
            type  yang:counter32;
        description
            "The number of outbound packets transmitted from the corresponding CPU
                    queue.";
        }
    }

    notification platform-cpu-queue-recovery {

        description "Notification to send information when CPU queue is recovered from full/high..";

        // severity "MINOR";
        // eventClass "STATE";
        leaf queue-id {
            type  uint8;
        description
            "This is a unique number representing each queue in CPU";
        }

        leaf queue-name {
            type  string;
        description
            "Queue Name corresponding to the Queue Id.";
        }

        leaf rate-percent {
            type  int8;
        description
            "Percentage of control packets transmitted in the CPU queue.
                    Value of -1 indicates rate percentage is not applicable.";
        }
    }

    notification platform-cpu-crc-error-packets {

        description "Notification to send information for CRC error packets received on the CPU interface..";

        // severity "WARNING";
        // eventClass "STATE";
        leaf bad-crc {
            type  yang:counter64;
        description
            "Last increment time of Bad CRC packets.
                    This is Updated at every 5sec interval.";
        }
    }

    notification platform-cpu-undersize-error-packets {

        description "Notification to send information for undersize error packets received on the CPU interface..";

        // severity "WARNING";
        // eventClass "STATE";
        leaf undersize-pkts {
            type  yang:counter64;
        description
            "Last inbound packets discarded whose size are less than
                    64 octets (which exclude framing bits, but include the FCS)
                    and have a good FCS value.
                    This is Updated at every 5sec interval.";
        }
    }

    notification platform-cpu-oversize-error-packets {

        description "Notification to send information for oversize error packets received on the CPU interface..";

        // severity "WARNING";
        // eventClass "STATE";
        leaf mtu-exceed {
            type  yang:counter64;
        description
            "Oversize Packets received";
        }
    }

    notification platform-cpu-fragment-error-packets {

        description "Notification to send information for fragment error packets received on the CPU interface..";

        // severity "WARNING";
        // eventClass "STATE";
        leaf fragments-pkts {
            type  yang:counter64;
        description
            "Last inbound packets discarded whose size are less than
                    64 octets (which exclude framing bits, but include the FCS)
                    and have a bad FCS value.
                    This is Updated at every 5sec interval.";
        }
    }

    notification platform-cpu-jabber-error-packets {

        description "Notification to send information for jabber error packets received on the CPU interface..";

        // severity "WARNING";
        // eventClass "STATE";
        leaf jabber-pkts {
            type  yang:counter64;
        description
            "Last inbound packets whose size are more than maximum
                    transmission unit size (which excludes framing bits, but include
                    FCS) and have a bad FCS value.
                    This is Updated at every 5sec interval.";
        }
    }

    notification platform-interface-crc-error-packets {

        description "Notification to send information for CRC error packets received on the interface..";

        // severity "WARNING";
        // eventClass "STATE";
        leaf name {
            type  string;
        description
            "The textual name of the interface. The value of this
                    object should
                    be the name of the interface as assigned by the local device and
                    should be suitable for use in commands entered at the device's
                    `console'. This might be a text name, such as `le0' or a simple
                    port number, such as `1', depending on the interface naming syntax
                    of the device. If several entries in the ifTable together represent
                    a single interface as named by the device, then each will have the
                    same value of name. Note that for an agent which responds to SNMP
                    queries concerning an interface on some other (proxied) device,
                    then the value of name for such an interface is the proxied
                    device's local name for it. If there is no local name, or this
                    object is otherwise not applicable, then this object contains a
                    zero-length string.";
        }

        leaf bad-crc {
            type  yang:counter64;
        description
            "Last increment time of Bad CRC packets.
                    This is Updated at every 5sec interval.";
        }
    }

    notification platform-interface-undersize-error-packets {

        description "Notification to send information for undersize error packets received on the interface..";

        // severity "WARNING";
        // eventClass "STATE";
        leaf name {
            type  string;
        description
            "The textual name of the interface. The value of this
                    object should
                    be the name of the interface as assigned by the local device and
                    should be suitable for use in commands entered at the device's
                    `console'. This might be a text name, such as `le0' or a simple
                    port number, such as `1', depending on the interface naming syntax
                    of the device. If several entries in the ifTable together represent
                    a single interface as named by the device, then each will have the
                    same value of name. Note that for an agent which responds to SNMP
                    queries concerning an interface on some other (proxied) device,
                    then the value of name for such an interface is the proxied
                    device's local name for it. If there is no local name, or this
                    object is otherwise not applicable, then this object contains a
                    zero-length string.";
        }

        leaf undersize-pkts {
            type  yang:counter64;
        description
            "Last inbound packets discarded whose size are less than
                    64 octets (which exclude framing bits, but include the FCS)
                    and have a good FCS value.
                    This is Updated at every 5sec interval.";
        }
    }

    notification platform-interface-oversize-error-packets {

        description "Notification to send information for oversize error packets received on the interface..";

        // severity "WARNING";
        // eventClass "STATE";
        leaf name {
            type  string;
        description
            "The textual name of the interface. The value of this
                    object should
                    be the name of the interface as assigned by the local device and
                    should be suitable for use in commands entered at the device's
                    `console'. This might be a text name, such as `le0' or a simple
                    port number, such as `1', depending on the interface naming syntax
                    of the device. If several entries in the ifTable together represent
                    a single interface as named by the device, then each will have the
                    same value of name. Note that for an agent which responds to SNMP
                    queries concerning an interface on some other (proxied) device,
                    then the value of name for such an interface is the proxied
                    device's local name for it. If there is no local name, or this
                    object is otherwise not applicable, then this object contains a
                    zero-length string.";
        }

        leaf mtu-exceed {
            type  yang:counter64;
        description
            "Oversize Packets received";
        }
    }

    notification platform-interface-fragment-error-packets {

        description "Notification to send information for fragment error packets received on the interface..";

        // severity "WARNING";
        // eventClass "STATE";
        leaf name {
            type  string;
        description
            "The textual name of the interface. The value of this
                    object should
                    be the name of the interface as assigned by the local device and
                    should be suitable for use in commands entered at the device's
                    `console'. This might be a text name, such as `le0' or a simple
                    port number, such as `1', depending on the interface naming syntax
                    of the device. If several entries in the ifTable together represent
                    a single interface as named by the device, then each will have the
                    same value of name. Note that for an agent which responds to SNMP
                    queries concerning an interface on some other (proxied) device,
                    then the value of name for such an interface is the proxied
                    device's local name for it. If there is no local name, or this
                    object is otherwise not applicable, then this object contains a
                    zero-length string.";
        }

        leaf fragments-pkts {
            type  yang:counter64;
        description
            "Last inbound packets discarded whose size are less than
                    64 octets (which exclude framing bits, but include the FCS)
                    and have a bad FCS value.
                    This is Updated at every 5sec interval.";
        }
    }

    notification platform-interface-jabber-error-packets {

        description "Notification to send information for jabber error packets received on the interface..";

        // severity "WARNING";
        // eventClass "STATE";
        leaf name {
            type  string;
        description
            "The textual name of the interface. The value of this
                    object should
                    be the name of the interface as assigned by the local device and
                    should be suitable for use in commands entered at the device's
                    `console'. This might be a text name, such as `le0' or a simple
                    port number, such as `1', depending on the interface naming syntax
                    of the device. If several entries in the ifTable together represent
                    a single interface as named by the device, then each will have the
                    same value of name. Note that for an agent which responds to SNMP
                    queries concerning an interface on some other (proxied) device,
                    then the value of name for such an interface is the proxied
                    device's local name for it. If there is no local name, or this
                    object is otherwise not applicable, then this object contains a
                    zero-length string.";
        }

        leaf jabber-pkts {
            type  yang:counter64;
        description
            "Last inbound packets whose size are more than maximum
                    transmission unit size (which excludes framing bits, but include
                    FCS) and have a bad FCS value.
                    This is Updated at every 5sec interval.";
        }
    }

}

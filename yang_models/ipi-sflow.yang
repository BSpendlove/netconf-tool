/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-sflow.yang
*
*/

module ipi-sflow {

    yang-version 1.1;

    namespace   "http://www.ipinfusion.com/yang/ocnos/ipi-sflow";

    prefix "ipi-sflow";

    import ipi-sflow-types {
        prefix ipi-sflow-types;
        revision-date 2021-09-03;
    }

    import ietf-inet-types {
        prefix inet;
        revision-date 2013-07-15;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "sFlow module provides user with the possibility to configure sFlow
                parameters";


    revision "2021-09-11" {
        description "Changing sflow container to presence container";
        reference "Initial Version";
    }

    revision "2021-09-03" {
        description "Update descriptions of attribute";
        reference "Initial Version";
    }

    revision "2021-07-30" {
        description "Sflow restructured";
        reference "Initial Version";
    }

    revision "2018-06-21" {
        description "Initial Version";
        reference "Initial Version";
    }

    grouping sflow-debug-terminal-state {
        description
            "sflowCMLSEPdebugCMLSEPterminalCMLSEPstate";
        leaf debug-options  {
            type  ipi-sflow-types:sflow_debug_type_t;
            description "Terminal debug sFlow debug level";
        } // END of debug-options definition.

    } // END of sflow-debug-terminal-state definition.
    grouping sflow-debug-terminal-top {
        description
            "sflowCMLSEPdebugCMLSEPterminalCMLSEPtop";
        container terminal {
            description
                "Container for terminal debug";
            container state {
                config false;
                description
                    "Operational state data";
                uses sflow-debug-terminal-state;
            } // END of state-container definition.
        } // END of terminal-container definition.
    } // END of sflow-debug-terminal-top definition.
    grouping sflow-debug-config {
        description
            "sflowCMLSEPdebugCMLSEPconfig";
        leaf debug-options  {
            type  ipi-sflow-types:sflow_debug_type_t;
            description "Set sFlow debug in config mode";
        } // END of debug-options definition.

    } // END of sflow-debug-config definition.
    grouping sflow-debug-top {
        description
            "sflowCMLSEPdebugCMLSEPtop";
        container debug {
            when " /ipi-sflow:sampling/ipi-sflow:sflow/ipi-sflow:config/ipi-sflow:enabled ";
            description
                "Container for sFlow debug";
            container config {
                description
                    "Container for sFlow debug configuration";
                uses sflow-debug-config;
            } // END of config-container definition.
            container state {
                config false;
                description
                    "Operational state data";
                uses sflow-debug-config;
            } // END of state-container definition.
            uses sflow-debug-terminal-top;
        } // END of debug-container definition.
    } // END of sflow-debug-top definition.
    grouping sflow-logging-config {
        description
            "sflowCMLSEPloggingCMLSEPconfig";
        leaf max-entries  {
            type  uint16 {
                 range "1000..10000"  {
                    description "1000..10000:Maximum number of cache entries. Default is 1000 entries";
                 }
            }
            default "1000";
            description "Specifies the maximum number of log entries that are cached, default
                        is 1000 entries";
        } // END of max-entries definition.

        leaf rate-limit  {
            if-feature feature-list:HAVE_BROADCOM;
            type  uint16 {
                 range "0..1000"  {
                    description "0..1000:Rate in packets per second. Default is 200 packets/sec";
                 }
            }
            default "200";
            description "Configures rate limits in packets per second, Default is 200
                        packets/sec";
        } // END of rate-limit definition.

    } // END of sflow-logging-config definition.
    grouping sflow-logging-top {
        description
            "sflowCMLSEPloggingCMLSEPtop";
        container logging {
            if-feature feature-list:HAVE_CUSTOM1_ACL;
            description
                "Container of sflow logging info";
            container config {
                description
                    "sFlow logging configuration parameters";
                uses sflow-logging-config;
            } // END of config-container definition.
            container state {
                config false;
                description
                    "sFlow logging state data";
                uses sflow-logging-config;
            } // END of state-container definition.
        } // END of logging-container definition.
    } // END of sflow-logging-top definition.
    grouping sflow-collector-config {
        description
            "sflowCMLSEPcollectorCMLSEPconfig";
        leaf address  {
            when " ../max-datagram-size + ../port + ../receiver-timeout ";
            type  inet:ipv4-address;
            description "The IP address of the sFlow collector.If set to 0.0.0.0 no sFlow
                        datagrams will be sent.";
        } // END of address definition.

        leaf port  {
            when " ../max-datagram-size + ../address + ../receiver-timeout ";
            type  inet:port-number {
                 range "1024..65535"  {
                    description "1024..65535:sFlow Collector Port Number";
                 }
            }
            description "The destination port for sFlow datagrams.Default port number is 6343.";
        } // END of port definition.

        leaf receiver-timeout  {
            when " ../max-datagram-size + ../port + ../address ";
            type  uint32 {
                 range "0..2147483647"  {
                    description "0..2147483647:Time Out value in second";
                 }
            }
            mandatory true;
            description "The time (in seconds) remaining before the sampler is released and
                        stops sampling. When set, the owner establishes control for the
                        specified period. When read, the remaining time in the interval is
                        returned.A management entity wanting to maintain control of the
                        sampler is responsible for setting a new value before the old one
                        expires.When the interval expires, the agent is responsible for
                        restoring all other entities in this row to their default values. It
                        must also free all other resources associated with this sFlowRcvrTable
                        entry.";
        } // END of receiver-timeout definition.

        leaf max-datagram-size  {
            when " ../address + ../port + ../receiver-timeout ";
            type  uint16 {
                 range "200..9000"  {
                    description "200..9000:Size in bytes";
                 }
            }
            mandatory true;
            description "The maximum number of data bytes that can be sent in a single sample
                        datagram. The manager should set this value to avoid fragmentation of
                        the sFlow datagrams.";
        } // END of max-datagram-size definition.

    } // END of sflow-collector-config definition.
    grouping sflow-collectors-top {
        description
            "sflowCMLSEPcollectorsCMLSEPtop";
        container collectors {
            when " /ipi-sflow:sampling/ipi-sflow:sflow/ipi-sflow:config/ipi-sflow:enabled ";
            description
                "sFlow collectors parameters";

            list collector {
                key "address port";
                max-elements 1;
                description
                    "sFlow collectors parameters";
                leaf address  {
                    type  leafref {
                        path  "../config/address";
                    }
                    description "The IP address of the sFlow collector.If set to 0.0.0.0 no sFlow
                                datagrams will be sent.";
                } // END of address definition.

                leaf port  {
                    type  leafref {
                        path  "../config/port";
                    }
                    description "The destination port for sFlow datagrams.Default port number is 6343.";
                } // END of port definition.

                container config {
                    description
                        "sFlow collectors configuration parameters";
                    uses sflow-collector-config;
                } // END of config-container definition.
                container state {
                    config false;
                    description
                        "sFlow collectors state data";
                    uses sflow-collector-config;
                } // END of state-container definition.
            } // End of collector-list
        } // END of collectors-container definition.
    } // END of sflow-collectors-top definition.
    grouping sflow-config {
        description
            "sflowCMLSEPconfig";
        leaf enabled  {
            type  empty;
            mandatory true;
            description "Use this attribute to enable or disable Sampling Flow (sFlow) feature
                        globally.";
        } // END of enabled definition.

        leaf source-address  {
            when " /ipi-sflow:sampling/ipi-sflow:sflow/ipi-sflow:config/ipi-sflow:enabled ";
            type  inet:ipv4-address;
            description "The IP address associated with this agent. In the case of a
                        multi-homed agent, this should be the loopback address of the agent.
                        The sFlowAgent address must provide SNMP connectivity to the agent.
                        The address should be an invariant that does not change as interfaces
                        are reconfigured, enabled, disabled,added or removed. A manager should
                        be able to use the sFlowAgentAddress as a unique key that will
                        identify this agent over extended periods of time so that a history
                        can be maintained.";
        } // END of source-address definition.

        leaf cpu-rate-limit  {
            if-feature feature-list:HAVE_BROADCOM;
            if-feature feature-list:NOT_HAVE_DUNE;
            type  uint32 {
                 range "2000..100000"  {
                    description "2000..100000:Rate in packets per second";
                 }
            }
            units "packets/s";
            description "CPU rate in packets per second";
        } // END of cpu-rate-limit definition.

    } // END of sflow-config definition.
    grouping sflow-state {
        description
            "sflowCMLSEPstate";
        leaf sflow-version  {
            type  string {
                length "1..1965";
                pattern "[^?' =,>|]+";
            }
            description "Uniquely identifies the version and implementation of this MIB.The MIB
                        Version willchange with each revision of the SFLOW MIB.Management
                        entities must check the MIB Version and not attempt to manage agents
                        with MIB Versions greater than that for which they were designed.";
        } // END of sflow-version definition.

        leaf datagram-version  {
            type  uint8;
            description "The version of sFlow datagrams that should be sent.When set to a value
                        not support by the agent, the agent should adjust the value to the
                        highest supported value less than the requested value, or return an
                        SNMP bad value error if no such value exists.";
        } // END of datagram-version definition.

    } // END of sflow-state definition.
    grouping sflow-top {
        description
            "sflowCMLSEPtop";
        container sflow {
            description
                "Container that stores all info about sflow";
            container config {
                presence "Enabling sampling Flow (sFlow) feature globally";
                description
                    "sFlow configuration parameters";
                uses sflow-config;
            } // END of config-container definition.
            container state {
                config false;
                description
                    "sFlow state data";
                uses sflow-config;
                uses sflow-state;
            } // END of state-container definition.
            uses sflow-collectors-top;
            uses sflow-logging-top;
            uses sflow-debug-top;
        } // END of sflow-container definition.
    } // END of sflow-top definition.

    grouping  sampling-grouping {
    description
        "Container for all data related to samplings";
    container sampling {
        description
            "Container for all data related to samplings";
        uses sflow-top;
    } // END of sampling-container definition.
    } // END of sampling-grouping definition.

    uses sampling-grouping;

    rpc sflow-terminal-debug-on {
        description "Enable sFlow debug categories";
        input  {
            leaf debug-options  {
                type ipi-sflow-types:sflow_debug_type_t;
                mandatory true;
                description "Bitmap representing sFlow debug categories";
            }
        }
    }

    rpc sflow-terminal-debug-off {
        description "Disable sFlow debug categories";
        input  {
            leaf debug-options  {
                type ipi-sflow-types:sflow_debug_type_t;
                mandatory true;
                description "Bitmap representing sFlow debug categories";
            }
        }
    }

    notification sflow-receiver-timeout-alarm-message {

        description "Notify alarm message.";

        // severity "MINOR";
        // eventClass "MESSAGE";
        leaf message {
            type string;
            description " alarm message notification";
        }
    }

}

module ipi-oc-platform-transceiver-deviations {
    namespace "http://www.ipinfusion.com/yang/ocnos/ipi-oc-platform-transceiver-deviations";
    prefix "ipi-oc-platform-transceiver-deviations";

    import openconfig-platform {
        prefix oc-platf;
    }

    import openconfig-platform-transceiver {
        prefix oc-transceiver;
    }

    revision "2021-05-10" {
        description
          "First release: add a type deviation for output-frequency";
    }

    deviation /oc-platf:components/oc-platf:component/oc-transceiver:transceiver/oc-transceiver:physical-channels/oc-transceiver:channel/oc-transceiver:state/oc-transceiver:output-frequency {
        deviate replace {
            type decimal64 {
                fraction-digits 6;
            }
        }
    }
}

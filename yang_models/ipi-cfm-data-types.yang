/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-cfm-data-types.yang
*
*/

module ipi-cfm-data-types {

    yang-version 1.1;

    namespace   "http://www.ipinfusion.com/yang/ocnos/ipi-cfm-data-types";

    prefix "ipi-cfm-data-types";

    organization
        "IP Infusion Inc.";

    contact
        "Address: 3965 Freedom Circle, Suite 200, Santa Clara, CA 95054
         Phone: +1 408-400-1900
         E-mail: support@ipinfusion.com
         Web: http://www.ipinfusion.com/";

    description
        "This module defines data types related to the CFM model";


    revision "2018-12-06" {
        description "Initial version drafted by referring MEF 38 and IEEE standards";
        reference " 0.1.0.";
    }



    typedef  cfm_bridge_type_t {
        type enumeration {
            enum vpws {
                value 1;
                description "Identifying string for VPWS instance";
            }
            enum evpn {
                value 2;
                description "Identifying string for EVPN instance";
            }
        }
        description "type definition for CFM_BRIDGE_TYPE_T";
    }

    typedef  cfm_rmep_mac_addr_t {
        type string;
        description "type definition for CFM_RMEP_MAC_ADDR_T";
    }

    typedef  cfm_rmep_id_string_t {
        type string;
        description "type definition for CFM_RMEP_ID_STRING_T";
    }

    typedef  cfm_rmep_type_t {
        type union {
            type cfm_rmep_mac_addr_t {

            }
            type cfm_rmep_id_string_t {

            }
        }
        description "type definition for CFM_RMEP_TYPE_T";
    }

    typedef  cfm_mip_creation_mode_t {
        type enumeration {
            enum none {
                value 1;
                description "No MIPs can be created for this VID";
            }
            enum default {
                value 2;
                description "MIP can be created if no lower active level or MEP at next lower active level";
            }
            enum explicit {
                value 3;
                description "MEP is needed at the next lower active level";
            }
        }
        description "type definition for CFM_MIP_CREATION_MODE_T";
    }

    typedef  cfm_id_permission_t {
        type enumeration {
            enum none {
                value 1;
                description "The Sender ID TLV is not to be sent";
            }
            enum chassis {
                value 2;
                description "The Chassis ID Length, Chassis ID Subtype, and Chassis ID fields of the Sender ID TLV are to be sent, but not the Management Address Length or Management Address fields";
            }
            enum manage {
                value 3;
                description "The Management Address Length and Management Address of the Sender ID TLV are to be sent, but the Chassis ID Length is to be transmitted with a 0 value, and the Chassis ID Subtype and Chassis ID fields not sent";
            }
            enum chassis-manage {
                value 4;
                description "The Chassis ID Length, Chassis ID Subtype, Chassis ID, Management Address Length, and Management Address fields are all to be sent";
            }
            enum defer {
                value 5;
                description "The contents of the Sender ID TLV are determined by the Maintenance Domain managed object";
            }
        }
        description "type definition for CFM_ID_PERMISSION_T";
    }

    typedef  cfm_md_type_t {
        type enumeration {
            enum no-name {
                value 1;
                description "No Maintenace Domain Name. MA type must be integer or ITU-T Carrier code (ICC) based format defined by ITU-T Y.1731";
            }
            enum character-string {
                value 4;
                description "MD name type is Character string. MA type must be string only";
            }
        }
        description "type definition for CFM_MD_TYPE_T";
    }

    typedef  cfm_ma_type_t {
        type enumeration {
            enum string {
                value 2;
                description "Character string as the ma-name. MD type should be string";
            }
            enum integer {
                value 3;
                description "Integer as ma-name. MD type should be no-name";
            }
            enum itu-t {
                value 32;
                description "ITU-T Carrier code (ICC) based format defined by ITU-T Y.1731. MD type should be no-name";
            }
        }
        description "type definition for CFM_MA_TYPE_T";
    }

    typedef  cfm_ma_mip_creation_mode_t {
        type enumeration {
            enum none {
                value 1;
                description "No MIPs can be created for this VID";
            }
            enum default {
                value 2;
                description "MIPs can be created if no lower active level or MEP at next lower active level";
            }
            enum explicit {
                value 3;
                description "MEP is needed at the next lower active level";
            }
            enum defer {
                value 4;
                description "Use the MIP creation permissions of the MD to which this MA belongs to";
            }
        }
        description "type definition for CFM_MA_MIP_CREATION_MODE_T";
    }

    typedef  cfm_ma_status_t {
        type enumeration {
            enum Unknown {
                value 0;
                description "MA connectivity status is unknown";
            }
            enum Active {
                value 1;
                description "MA connectivity status is active";
            }
            enum Partially-Active {
                value 2;
                description "MA connectivity status is partially active";
            }
            enum Not-Active {
                value 3;
                description "MA connectivity status is not active";
            }
            enum Error {
                value 4;
                description "MA connectivity status has some error";
            }
        }
        description "type definition for CFM_MA_STATUS_T";
    }

    typedef  cfm_mep_direction_t {
        type enumeration {
            enum down {
                value 1;
                description "Down MEP";
            }
            enum up {
                value 2;
                description "Up MEP";
            }
        }
        description "type definition for CFM_MEP_DIRECTION_T";
    }

    typedef  cfm_mep_state_t {
        type enumeration {
            enum false {
                value 0;
                description "MEP to cease functioning";
            }
            enum true {
                value 1;
                description "MEP to function normally";
            }
        }
        description "type definition for CFM_MEP_STATE_T";
    }

    typedef  cfm_mep_connectivity_status_t {
        type enumeration {
            enum Fully-Connected {
                value 1;
                description "MEP connectivity status is Fully Connected";
            }
            enum Partially-Connected {
                value 2;
                description "MEP connectivity status is Partially-Connected";
            }
            enum Isolated {
                value 3;
                description "MEP connectivity status is Isolated";
            }
        }
        description "type definition for CFM_MEP_CONNECTIVITY_STATUS_T";
    }

    typedef  cfm_mep_uni_t {
        type enumeration {
            enum uni-mep {
                value 1;
                description "UNI-MEG MEP to intimate the UNI type";
            }
        }
        description "type definition for CFM_MEP_UNI_T";
    }

    typedef  cfm_ccm_interval_t {
        type enumeration {
            enum 3ms {
                value 1;
                description "CC Interval 3 millisecond";
            }
            enum 10ms {
                value 2;
                description "CC Interval 10 millisecond";
            }
            enum 100ms {
                value 3;
                description "CC Interval 100 millisecond";
            }
            enum 1s {
                value 4;
                description "CC Interval 1 second(default)";
            }
            enum 10s {
                value 5;
                description "CC Interval 10 second";
            }
        }
        description "type definition for CFM_CCM_INTERVAL_T";
    }

    typedef  cfm_mep_lck_t {
        type enumeration {
            enum unlock {
                value 0;
                description "Disable adminstrative locking state";
            }
            enum lock {
                value 1;
                description "Enable adminstrative locking state";
            }
        }
        description "type definition for CFM_MEP_LCK_T";
    }

    typedef  cfm_mep_lowest_fault_priority_t {
        type enumeration {
            enum defRDICCM {
                value 1;
                description "DefRDICCM";
            }
            enum defMACstatus {
                value 2;
                description "DefMACstatus";
            }
            enum defRemoteCCM {
                value 3;
                description "DefRemoteCCM";
            }
            enum defErrorCCM {
                value 4;
                description "DefErrorCCM";
            }
            enum defXconCCM {
                value 5;
                description "DefXconCCM";
            }
        }
        description "type definition for CFM_MEP_LOWEST_FAULT_PRIORITY_T";
    }

    typedef  cfm_mep_highest_fault_defect_t {
        type enumeration {
            enum none {
                value 1;
                description "No defects since FNG_RESET";
            }
            enum defRDICCM {
                value 2;
                description "DefRDICCM";
            }
            enum defMACstatus {
                value 3;
                description "DefMACstatus";
            }
            enum defRemoteCCM {
                value 4;
                description "DefRemoteCCM";
            }
            enum defErrorCCM {
                value 5;
                description "DefErrorCCM";
            }
            enum defXconCCM {
                value 6;
                description "DefXconCCM";
            }
        }
        description "type definition for CFM_MEP_HIGHEST_FAULT_DEFECT_T";
    }

    typedef  cfm_received_ccm_defect_t {
        type bits {
            bit none {
                position 0;
                description "No defects in last CCM PDU";
            }
            bit defRDICCM {
                position 1;
                description "A remote MEP is reported the RDI bit set in its last CCM";
            }
            bit defMACstatus {
                position 2;
                description "One or more of the remote MEPs is reporting a failure in its Port Status TLV or Interface Status TLV";
            }
            bit defRemoteCCM {
                position 3;
                description "Atleast one of the MEP is not receiving valid CCMs from one of the its remote MEP";
            }
            bit defErrorCCM {
                position 4;
                description "The MEP has received at least one invalid CCM whose CCM Interval has not yet timed out";
            }
            bit defXconCCM {
                position 5;
                description "The MEP has received at least one CCM from either another MAID or a lower MD Level whose CCM Interval has not yet timed out";
            }
        }
        description "type definition for CFM_RECEIVED_CCM_DEFECT_T";
    }

    typedef  cfm_mep_defects_bit_t {
        type bits {
            bit defRDICCM {
                position 0;
                description "A remote MEP is reported the RDI bit set in its last CCM";
            }
            bit defMACstatus {
                position 1;
                description "One or more of the remote MEPs is reporting a failure in its Port Status TLV or Interface Status TLV";
            }
            bit defRemoteCCM {
                position 2;
                description "Atleast one of the MEP is not receiving valid CCMs from one of the its remote MEP";
            }
            bit defErrorCCM {
                position 3;
                description "The MEP has received at least one invalid CCM whose CCM Interval has not yet timed out";
            }
            bit defXconCCM {
                position 4;
                description "The MEP has received at least one CCM from either another MAID or a lower MD Level whose CCM Interval has not yet timed out";
            }
        }
        description "type definition for CFM_MEP_DEFECTS_BIT_T";
    }

    typedef  cfm_start_time_t {
        type enumeration {
            enum immediate {
                value 1;
                description "Start the measurement session immediately";
            }
        }
        description "type definition for CFM_START_TIME_T";
    }

    typedef  cfm_stop_time_t {
        type enumeration {
            enum none {
                value 0;
                description "Never end the measurement session";
            }
        }
        description "type definition for CFM_STOP_TIME_T";
    }

    typedef  cfm_absolute_time_t {
        type enumeration {
            enum absolute {
                value 3;
                description "This object specifies the scheduled start/stop date/time to perform the on-demand Performance Monitoring OAM operations";
            }
        }
        description "type definition for CFM_ABSOLUTE_TIME_T";
    }

    typedef  cfm_relative_time_t {
        type enumeration {
            enum relative {
                value 2;
                description "This object specifies the relative start/stop time from the current system time to perform on-demand Performance Monitoring OAM operations";
            }
        }
        description "type definition for CFM_RELATIVE_TIME_T";
    }

    typedef  cfm_lm_measurement_type_t {
        type enumeration {
            enum lmm {
                value 1;
                description "LMM SOAM PDU generated and received LMR responses tracked";
            }
            enum slm {
                value 2;
                description "SLM SOAM PDU generated and received SLR responses tracked(default)";
            }
            enum ccm {
                value 3;
                description "CCM SOAM PDU generated and received CCM PDUs tracked";
            }
        }
        description "type definition for CFM_LM_MEASUREMENT_TYPE_T";
    }

    typedef  cfm_lm_measurement_type_reply_t {
        type enumeration {
            enum lmm {
                value 1;
                description "LMM SOAM PDU generated and received LMR responses tracked";
            }
            enum slm {
                value 2;
                description "SLM SOAM PDU generated and received SLR responses tracked(default)";
            }
        }
        description "type definition for CFM_LM_MEASUREMENT_TYPE_REPLY_T";
    }

    typedef  cfm_session_status_t {
        type enumeration {
            enum active {
                value 1;
                description "Indicates the measurement instance is active";
            }
            enum not-active {
                value 2;
                description "Indicates the measurement instance is not active";
            }
        }
        description "type definition for CFM_SESSION_STATUS_T";
    }

    typedef  cfm_y1731_tx_interval_t {
        type enumeration {
            enum one-second {
                value 1;
                description "Transmit interval one second";
            }
            enum one-minute {
                value 60;
                description "Transmit interval one minute";
            }
        }
        description "type definition for CFM_Y1731_TX_INTERVAL_T";
    }

    typedef  cfm_mep_fng_state_t {
        type enumeration {
            enum reset {
                value 0;
                description "No defect has been present since the fng-reset-time timer expired or since the state machine was last reset";
            }
            enum defect {
                value 1;
                description "A defect is present but not for a long enough time to be reported (fng-alarm-time)";
            }
            enum report-defect {
                value 2;
                description "A momentary state during which the defect is reported by sending a fault-alarm notificationif that action is enabled";
            }
            enum defect-reported {
                value 3;
                description "A defect is present and some defect has been reported";
            }
            enum defect-clearing {
                value 4;
                description "No defect is present but the fng-reset-time timer has not yet expired";
            }
        }
        description "type definition for CFM_MEP_FNG_STATE_T";
    }

    typedef  cfm_relay_action_t {
        type enumeration {
            enum hit {
                value 0;
                description "Indicates the LTM reached an MP whose MAC address matches the target MAC address";
            }
            enum filtering-database {
                value 1;
                description "Indicates the Egress Port was determined by consulting the Filtering Database";
            }
            enum mip-ccm-database {
                value 2;
                description "Indicates the Egress Port was determined by consulting the MIP CCM Database";
            }
        }
        description "type definition for CFM_RELAY_ACTION_T";
    }

    typedef  cfm_ingress_action_t {
        type enumeration {
            enum ok {
                value 0;
                description "Indicates the target data frame would be passed through to the MAC Relay Entity";
            }
            enum down {
                value 1;
                description "Indicates the Bridge Ports MAC Operational parameter is false";
            }
            enum blocked {
                value 2;
                description "Indicates the target data frame would not be forwarded if received on this Port due to active topology enforcement";
            }
            enum vid {
                value 3;
                description "Indicates the ingress port is not in the member set of the LTMs VID, and ingress filtering is enabled, so the target data frame would be filtered by ingress filtering";
            }
        }
        description "type definition for CFM_INGRESS_ACTION_T";
    }

    typedef  cfm_port_status_tlv_t {
        type enumeration {
            enum no-status-tlv {
                value 0;
                description "Indicates either that no CCM has been received or that no port status TLV was present in the last CCM received";
            }
            enum blocked {
                value 1;
                description "Ordinary data cannot pass freely through the port on which the remote MEP resides. Value of enableRmepDefect is false";
            }
            enum up {
                value 2;
                description "Ordinary data can pass freely through the port on which the remote MEP resides. Value of enableRmepDefect is true";
            }
        }
        description "type definition for CFM_PORT_STATUS_TLV_T";
    }

    typedef  cfm_interface_status_tlv_t {
        type enumeration {
            enum no-status-tlv {
                value 0;
                description "Indicates either that no CCM has been received or that no interface status TLV was present in the last CCM received";
            }
            enum up {
                value 1;
                description "The interface is ready to pass packets";
            }
            enum down {
                value 2;
                description "The interface cannot pass packets";
            }
            enum testing {
                value 3;
                description "The interface is in some test mode";
            }
            enum unknown {
                value 4;
                description "The interface status cannot be determined for some reason";
            }
            enum dormant {
                value 5;
                description "The interface is not in a state to pass packets but is in a pending state, waiting for some external event";
            }
            enum not-present {
                value 6;
                description "Some component of the interface is missing";
            }
            enum lower-layer-down {
                value 7;
                description "The interface is down due to state of the lower layer interfaces";
            }
        }
        description "type definition for CFM_INTERFACE_STATUS_TLV_T";
    }

    typedef  cfm_egress_action_t {
        type enumeration {
            enum ok {
                value 0;
                description "Indicates the targeted data frame would be forwarded";
            }
            enum down {
                value 1;
                description "Indicates the Egress Port can be identified but that Bridge Ports MAC Operational parameter is false";
            }
            enum blocked {
                value 2;
                description "Indicates the Egress Port can be identified but the data frame would not pass through the the Egress Port due to active topology management i.e the Bridge Port is not in the Forwarding state";
            }
            enum vid {
                value 3;
                description "Indicates the Egress Port can be identified but the Bridge Port is not in the LTMs VIDs member set, so would be filtered by egress filtering";
            }
        }
        description "type definition for CFM_EGRESS_ACTION_T";
    }

    typedef  cfm_portid_subtype_t {
        type enumeration {
            enum interface-alias {
                value 1;
                description "The ifAlias field from the Interfaces Group MIB";
            }
            enum port-component {
                value 2;
                description "EntPhysicalAlias when entPhysClass has a value of port(10) or backplane(4)";
            }
            enum mac-address {
                value 3;
                description "A MAC address";
            }
            enum network-address {
                value 4;
                description "network-address is an octet string that identifies a particular network address family and an associated network address that are encoded in network octet order";
            }
            enum interface-name {
                value 5;
                description "The name field from the Interfaces Group MIB";
            }
            enum agent-circuit-id {
                value 6;
                description "Agent circuit ID";
            }
            enum local {
                value 7;
                description "A locally defined identifier";
            }
        }
        description "type definition for CFM_PORTID_SUBTYPE_T";
    }

    typedef  cfm_chassis_id_subtype_t {
        type enumeration {
            enum chassis-component {
                value 1;
                description "This leaf contains the content of EntPhysicalAlias when entPhysClass has a value of chassis(3)";
            }
            enum interface-alias {
                value 2;
                description "The IfAlias field from the Interfaces Group MIB";
            }
            enum port-component {
                value 3;
                description "The EntPhysicalAlias from the Interfaces Group MIB when entPhysClass has a value of port(10) or backplane(4)";
            }
            enum mac-address-type {
                value 4;
                description "An IEEE 802-2001 Ethernet MAC Address";
            }
            enum network-address {
                value 5;
                description "It's an octet string that identifies a particular network address family and an associated network address that are encoded in network octet order";
            }
            enum interface-name {
                value 6;
                description "name";
            }
            enum local {
                value 7;
                description "A locally assigned alpha-numeric string";
            }
        }
        description "type definition for CFM_CHASSIS_ID_SUBTYPE_T";
    }

    typedef  cfm_dm_measurement_type_t {
        type enumeration {
            enum dmm {
                value 1;
                description "DMM SOAM PDU generated. DMR responses received";
            }
            enum dm1-transmitted {
                value 2;
                description "1DM SOAM PDU generated";
            }
            enum dm1-received {
                value 3;
                description "1DM SOAM PDU received and tracked";
            }
        }
        description "type definition for CFM_DM_MEASUREMENT_TYPE_T";
    }

    typedef  cfm_dm_interval_t {
        type enumeration {
            enum 1s {
                value 4;
                description "DM PDU Interval 1 second";
            }
            enum 10s {
                value 5;
                description "DM PDU Interval 10 second";
            }
        }
        description "type definition for CFM_DM_INTERVAL_T";
    }

    typedef  cfm_dm_data_pattern_t {
        type enumeration {
            enum zeroes {
                value 1;
                description "Indicates the Data TLV contains all zeros";
            }
            enum ones {
                value 2;
                description "Indicates the Data TLV contains all ones";
            }
        }
        description "type definition for CFM_DM_DATA_PATTERN_T";
    }

    typedef  cfm_dm_measurement_bin_type_t {
        type enumeration {
            enum frame-delay {
                value 1;
                description "Indicates a measurement bin for two-way Frame Delay";
            }
            enum inter-frame-delay-variation {
                value 4;
                description "Indicates a measurement bin for two-way Inter-frame Delay Variation";
            }
        }
        description "type definition for CFM_DM_MEASUREMENT_BIN_TYPE_T";
    }

    typedef  cfm_debug_t {
        type bits {
            bit events {
                position 0;
                description "Enable event debugs";
            }
            bit rx {
                position 1;
                description "Enable receive debugs";
            }
            bit tx {
                position 2;
                description "Enable transmit debugs";
            }
            bit loopback {
                position 3;
                description "Enable loopback debugs";
            }
            bit traceroute {
                position 4;
                description "Enable traceroute debugs";
            }
        }
        description "type definition for CFM_DEBUG_T";
    }

    typedef  cfm_test_type_t {
        type enumeration {
            enum in-service {
                value 0;
                description "This indicates the ETH-Test is in-service and normal client service traffic is not interrupted.";
            }
            enum out-of-service {
                value 1;
                description "This indicates the ETH-Test is out-of-service and normal client service traffic is disrupted.";
            }
        }
        description "type definition for CFM_TEST_TYPE_T";
    }

    typedef  cfm_test_pattern_type_t {
        type enumeration {
            enum null-sig {
                value 1;
                description "This test pattern is a Null signal without CRC-32";
            }
            enum null-sig-crc32 {
                value 2;
                description "This test pattern is a Null signal with CRC-32";
            }
            enum prbs {
                value 3;
                description "This test pattern is a PRBS 2^31-1 without CRC-32.";
            }
            enum prbs-crc32 {
                value 4;
                description "This test pattern is a PRBS 2^31-1 with CRC-32.";
            }
        }
        description "type definition for CFM_TEST_PATTERN_TYPE_T";
    }

    typedef  cfm_test_node_type_t {
        type enumeration {
            enum generator {
                value 1;
                description "The node will act as a ETH-TST Frame Generator";
            }
            enum receiver {
                value 2;
                description "The node will act as a ETH-TST Frame Receiver";
            }
            enum both {
                value 3;
                description "The node will act as both ETH-TST Frame Generator and Receiver";
            }
        }
        description "type definition for CFM_TEST_NODE_TYPE_T";
    }

}

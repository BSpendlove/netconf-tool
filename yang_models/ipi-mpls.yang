/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-mpls.yang
*
*/

module ipi-mpls {

    yang-version 1.1;

    namespace   "http://www.ipinfusion.com/yang/ocnos/ipi-mpls";

    prefix "ipi-mpls";

    import cml-data-types {
        prefix cml-data-types;
        revision-date 2022-04-04;
    }

    import ipi-mpls-types {
        prefix ipi-mpls-types;
        revision-date 2022-02-15;
    }

    import ipi-interface {
        prefix ipi-interface;
        revision-date 2022-04-05;
    }

    import ipi-if-aggregate {
        prefix ipi-if-aggregate;
        revision-date 2022-04-20;
    }

    import ietf-yang-types {
        prefix yang;
        revision-date 2013-07-15;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "Data model for MPLS";


    revision "2022-04-22" {
        description "Suncom patch merge";
        reference " 0.5.10.";
    }

    revision "2021-12-08" {
        description "Updated six-pe-tunnel-policy objectlist for single instance";
        reference " 0.5.9.";
    }

    revision "2021-09-01" {
        description "Changed base interface module's switchport attribute name and the datatype from bool to empty";
        reference " 0.5.8.";
    }

    revision "2021-08-17" {
        description "Added runtime attributes for operational state of RSVP and LDP graceful-restart";
        reference " 0.5.7.";
    }

    revision "2021-08-02" {
        description "Added support for multiple inner vlan Range or ID in MPLS service template";
        reference " 0.5.5.";
    }

    revision "2021-07-29" {
        description "Added bandwidth cli for IGP TE";
        reference " 0.5.6.";
    }

    revision "2021-07-12" {
        description "Corrected inner vlan data-type for MPLS service template";
        reference " 0.5.4.";
    }

    revision "2021-06-29" {
        description "Corrected length property for group-name";
        reference " 0.5.3.";
    }

    revision "2021-06-25" {
        description "Removed implicit delete from config container of service-template config as not required ";
        reference " 0.5.2.";
    }

    revision "2021-05-13" {
        description "Corrected dependencies for label-management object lists";
        reference " 0.5.1.";
    }

    revision "2021-03-30" {
        description "Change for Tunnel policy config";
        reference " 0.5.0.";
    }

    revision "2021-03-15" {
        description "Change for restructuring Diffserve-TE";
        reference " 0.4.0.";
    }

    revision "2021-01-27" {
        description "Change for restructuring Label Management and admin group CLIs";
        reference " 0.3.0.";
    }

    revision "2020-12-15" {
        description "Change to have data-types in lower case instead of camel case";
        reference " 0.2.0.";
    }

    revision "2020-11-03" {
        description "Initial Version";
        reference " 0.1.0.";
    }

    grouping tunnel-policies-config {
        description
            "configuration parameters for tunnel policy";
        leaf name  {
            type  string {
                length "1..1965";
                pattern "[^?' =,>|]+";
            }
            description "Name for the tunnel policy";
        } // END of name definition.

        leaf-list color-code  {
            type  uint32 {
                 range "1..4294967295"  {
                    description "1..4294967295:Color to be used";
                 }
            }
            description "Use this attribute to configure color for tunnel policy";
        } // END of color-code definition.

        leaf selection-mode  {
            type  ipi-mpls-types:mpls_tunnel_selection_mode_t;
            default "dedicated";
            description "Use this attribute to configure selection mode for tunnel policy";
        } // END of selection-mode definition.

        leaf tunnel-type  {
            type  cml-data-types:cml_mpls_tunnel_selection_type_t;
            description "Use this attribute to configure selection mode for tunnel policy";
        } // END of tunnel-type definition.

    } // END of tunnel-policies-config definition.
    grouping mpls-6pe-tunnel-policy {
        description
            "MPLS 6PE tunnel policy Configurations";
        leaf name  {
            type  string {
                length "1..1965";
                pattern "[^?' =,>|]+";
            }
            description "Use this attribute to map Tunnel policy to 6PE";
        } // END of name definition.

    } // END of mpls-6pe-tunnel-policy definition.
    grouping nsm-client-graceful-restart-state {
        description
            "Operational parameters for rsvp/ldp graceful-restart";
        leaf graceful-restart-state  {
            type  ipi-mpls-types:mpls_graceful_restart_status_t;
            description "State of ldp/rsvp graceful restart";
        } // END of graceful-restart-state definition.

        leaf remaining-restart-time  {
            type  uint32;
            units "seconds";
            description "remaining ldp/rsvp graceful restart time";
        } // END of remaining-restart-time definition.

        leaf disconnected-time  {
            type  yang:date-and-time {
                pattern "\\d{4}-\\d{2}-\\d{2}T\\d{2}:\\d{2}:\\d{2}(\\.\\d+)?(Z|[\\+\\-]\\d{2}:\\d{2})";
                }
                description "ldp/rsvp disconnected time";
            } // END of disconnected-time definition.

    } // END of nsm-client-graceful-restart-state definition.
    grouping mpls-global-config {
        description
            "MPLS global configuration";
        leaf local-packet-handling  {
            type  empty;
            description "Use this attribute to enable the labeling of locally generated TCP
                        packets. All other locally generated packets are not looked at by the
                        MPLS Forwarder";
        } // END of local-packet-handling definition.

        leaf lsp-stitching  {
            type  empty;
            description "Use this attribute to enable lsp stitching for ILM and installed FTM";
        } // END of lsp-stitching definition.

        leaf propagate-ttl  {
            type  empty;
            description "Use this attribute to enable TTL propagation. Enabling TTL propagation
                        causes the TTL value in the IP header to be copied onto the TTL field
                        in the shim header, at the LSP ingress";
        } // END of propagate-ttl definition.

        leaf ingress-ttl-value  {
            type  uint8 {
                 range "0..255"  {
                    description "0..255:TTL value to be used";
                 }
            }
            description "Use this attribute to set a Time to Live (TTL) value for LSPs for
                        which this LSR is the ingress.";
        } // END of ingress-ttl-value definition.

        leaf egress-ttl-value  {
            if-feature feature-list:NOT_HAVE_USER_HSL;
            type  uint8 {
                 range "0..255"  {
                    description "0..255:TTL value to be used";
                 }
            }
            description "mpls egress-ttl . Use this attribute to set a custom Time to Live
                        (TTL) value for LSPs for which this LSR is the egress";
        } // END of egress-ttl-value definition.

        leaf lsp-model-uniform  {
            type  empty;
            description "Use this attribute to configure the MPLS LSP model as Uniform.";
        } // END of lsp-model-uniform definition.

    } // END of mpls-global-config definition.
    grouping mpls-debug-config {
        description
            "Grouping for MPLS Debug Level Configurations";
        leaf mpls-log-options  {
            type  cml-data-types:cml_nsm_mpls_log_t;
            description "Use this attribute to exercise logging control. This command interacts
                        with the Linux kernel. When using the kernel logging utility - klogd -
                        it needs to be enabled to a logging level that allows for the
                        requested log messages to be printed.";
        } // END of mpls-log-options definition.

    } // END of mpls-debug-config definition.
    grouping mpls-interface-label-switching-config {
        description
            "interface label switching configuration";
        leaf enable  {
            type  empty;
            mandatory true;
            description "Use this attribute to enable label-switching on a TE link";
        } // END of enable definition.

        leaf label-space  {
            type  uint16 {
                 range "0..60000"  {
                    description "0..60000:label space value";
                 }
            }
            description "Use this attribute to specify label-space for the interface, at
                        present only label space 0 is supported";
        } // END of label-space definition.

    } // END of mpls-interface-label-switching-config definition.
    grouping mpls-admin-group-config {
        description
            "MPLS Administrative Group Configurations";
        leaf name  {
            type  string {
                length "1..1965";
                pattern "[^?' =,>|]+";
            }
            description "Use this attribute to create a name-to-value binding for an
                        administrative group";
        } // END of name definition.

        leaf id  {
            type  uint8 {
                 range "0..31"  {
                    description "0..31:Value of administrative group to be added";
                 }
            }
            description "identifier value for the administrative group";
        } // END of id definition.

    } // END of mpls-admin-group-config definition.
    grouping mpls-interface-bandwidth-config {
        description
            "MPLS Interface Bandwidth Configurations";
        leaf-list admin-group-name  {
            if-feature feature-list:HAVE_TE;
            type  leafref {
                path  "/mpls/admin-group/name";
            }
            description "Use this attribute to create an administrative group to be used for
                        links. Each link can be a member of one or more, or no administrative
                        groups.this attribute adds link between an interface and a group. The
                        name is the name of the group previously configured. There can be
                        multiple groups per interface.";
        } // END of admin-group-name definition.

        leaf bandwidth  {
            if-feature feature-list:HAVE_TE;
            if-feature feature-list:NOT_IF_BANDWIDTH_INFO;
            type  string {
                length "1..1965";
                pattern "[^?' =,>|]+";
            }
            default "0";
            description "Use this attribute to specify a discrete, maximum bandwidth value for
                        the interface. The bandwidth attribute takes input in kbps, mbps and
                        gbps.";
        } // END of bandwidth definition.

        leaf reservable-bandwidth  {
            when " /ipi-interface:interfaces/ipi-interface:interface/ipi-interface:config/ipi-interface:enable-switchport != '1' ";
            if-feature feature-list:HAVE_TE;
            type  string {
                length "1..1965";
                pattern "[^?' =,>|]+";
            }
            description "Use this attribute to specify the maximum reservable bandwidth per
                        interface. This value can be equal or smaller value than
                        max-bandwidth.";
        } // END of reservable-bandwidth definition.

        leaf-list shared-risk-link-group  {
            if-feature feature-list:HAVE_SRLG;
            type  uint32 {
                 range "0..4294967295"  {
                    description "0..4294967295:Group number";
                 }
            }
            description "Use this attribute to add the link to a srlg group";
        } // END of shared-risk-link-group definition.

        leaf uni-available-bandwidth  {
            if-feature feature-list:HAVE_TE;
            if-feature feature-list:NOT_IF_BANDWIDTH_INFO;
            type  string {
                length "1..1965";
                pattern "[^?' =,>|]+";
            }
            description "Use this attribute to specify a unidirectional, available bandwidth
                        value for the interface. The bandwidth attribute takes input in kbps,
                        mbps and gbps.";
        } // END of uni-available-bandwidth definition.

        leaf uni-residual-bandwidth  {
            if-feature feature-list:HAVE_TE;
            if-feature feature-list:NOT_IF_BANDWIDTH_INFO;
            type  string {
                length "1..1965";
                pattern "[^?' =,>|]+";
            }
            description "Use this attribute to specify a unidirectional, residual bandwidth
                        value for the interface. The bandwidth attribute takes input in kbps,
                        mbps and gbps.";
        } // END of uni-residual-bandwidth definition.

        leaf uni-utilized-bandwidth  {
            if-feature feature-list:HAVE_TE;
            if-feature feature-list:NOT_IF_BANDWIDTH_INFO;
            type  string {
                length "1..1965";
                pattern "[^?' =,>|]+";
            }
            description "Use this attribute to specify a unidirectional, utilised bandwidth
                        value for the interface. The bandwidth attribute takes input in kbps,
                        mbps and gbps.";
        } // END of uni-utilized-bandwidth definition.

    } // END of mpls-interface-bandwidth-config definition.
    grouping mpls-bandwidth-class-config {
        description
            "MPLS Bandwidth Class Configurations";
        leaf name  {
            type  string {
                length "1..1965";
                pattern "[^?' =,>|]+";
            }
            description "Use this attribute to create a new bandwidth class name. Using this
                        command changes the command mode to Bandwidth-class mode";
        } // END of name definition.

    } // END of mpls-bandwidth-class-config definition.
    grouping mpls-bandwidth-properties-config {
        description
            "MPLS Bandwidth Class without DSTE Configurations";
        leaf max-bandwidth  {
            type  string {
                length "1..1965";
                pattern "[^?' =,>|]+";
            }
            mandatory true;
            description "Use this attribute to specify the maximum bandwidth to be used for a
                        bandwidth-class. The bandwidth value is in bits";
        } // END of max-bandwidth definition.

        leaf setup-priority  {
            type  uint8 {
                 range "0..7"  {
                    description "0..7:Setup Priority value <0-7>";
                 }
            }
            mandatory true;
            description "Use this attribute to specify the maximum bandwidth to be used for a
                        bandwidth-class. The bandwidth value is in bits";
        } // END of setup-priority definition.

        leaf hold-priority  {
            type  uint8 {
                 range "0..7"  {
                    description "0..7:Hold Priority value <0-7>";
                 }
            }
            mandatory true;
            description "Use this attribute to specify the maximum bandwidth to be used for a
                        bandwidth-class. The bandwidth value is in bits";
        } // END of hold-priority definition.

    } // END of mpls-bandwidth-properties-config definition.
    grouping label-space-config {
        description
            "Label space configuration";
        leaf label-space-name  {
            type  uint16 {
                 range "0..60000"  {
                    description "0..60000:Label-space value";
                 }
            }
            description "This attribute identifies the label space";
        } // END of label-space-name definition.

    } // END of label-space-config definition.
    grouping label-range-config {
        description
            "Label Range configuration";
        leaf min-label  {
            type  uint32 {
                 range "16..1048575"  {
                    description "16..1048575:Minimum size to be used for label pools or protocol range";
                 }
            }
            mandatory true;
            description "Use this attribute to configure a minimum label value for a label
                        space. After setting a minimum label value for a label space, make
                        sure to bind the label space to an interface.";
        } // END of min-label definition.

        leaf max-label  {
            type  uint32 {
                 range "16..1048575"  {
                    description "16..1048575:Maximum size to be used for label pools or protocol range";
                 }
            }
            mandatory true;
            description "Use this attribute to configure a maximum label value for a label
                        space. After setting a maximum label value for a label space, make
                        sure to bind the label space to an interface";
        } // END of max-label definition.

    } // END of label-range-config definition.
    grouping module-label-range-config {
        description
            "Module Label Range configurations";
        leaf module-name  {
            type  ipi-mpls-types:mpls_module_t;
            description "Use this attribute to specify the protocol module for which label
                        range is specified";
        } // END of module-name definition.

        uses label-range-config;
    } // END of module-label-range-config definition.
    grouping mpls-supported-diffserv-classes-config {
        description
            "Supported MPLS diffServe class configuration";
        leaf supported-class-name  {
            type  string {
                length "1..1965";
                pattern "[^?' =,>|]+";
            }
            description "Use this attribute to configure a DiffServ class.";
        } // END of supported-class-name definition.

    } // END of mpls-supported-diffserv-classes-config definition.
    grouping mpls-class-exp-bit-config {
        description
            "Grouping for MPLS diffServe class to expbit mapping parameters";
        leaf supported-class-name  {
            type  string {
                length "1..1965";
                pattern "[^?' =,>|]+";
            }
            description "Use this attribute to configure a DiffServ class.";
        } // END of supported-class-name definition.

        leaf exp-bit  {
            type  uint8 {
                 range "0..7"  {
                    description "0..7:EXP bit to be mapped to";
                 }
            }
            description "EXP bit to map to the supported class.";
        } // END of exp-bit definition.

    } // END of mpls-class-exp-bit-config definition.
    grouping l2vpn-customer-service-map-state {
        description
            "Grouping for Operational attributes for service-template mapping list";
        leaf vpls-name  {
            type  string {
                length "1..1965";
                pattern "[^?' =,>|]+";
            }
            description "Use this attribute to retrieve confgiured VPLS instance details";
        } // END of vpls-name definition.

        leaf error-status  {
            type  ipi-mpls-types:mpls_l2vpn_serv_temp_error_status_t;
            description "Use this attribute to retrieve error status";
        } // END of error-status definition.

        leaf binding-interface-name  {
            type  string {
                length "1..1965";
                pattern "[^?' =,>|]+";
            }
            description "Use this attribute to retrieve binded interface details for a
                        confgiured VPLS instance";
        } // END of binding-interface-name definition.

    } // END of l2vpn-customer-service-map-state definition.
    grouping l2vpn-access-circuit-group-config {
        description
            "Grouping for Configuration attributes for access-circuit-group";
        leaf group-name  {
            type  string {
                length "1..32";
                pattern "[^?' =,>|]+";
            }
            description "Use this attribute to create a new access circuit group for MPLS";
        } // END of group-name definition.

        leaf group-identifier  {
            type  uint32 {
                 range "1..4294967295"  {
                    description "1..4294967295:Identifier for the group (group-id to be used in LDP)";
                 }
            }
            mandatory true;
            description "Specify group identifier for access circuit group";
        } // END of group-identifier definition.

    } // END of l2vpn-access-circuit-group-config definition.
    grouping l2vpn-access-circuit-group-top {
        description
            "Top level Grouping for access-circuit-group";

        list access-circuit-group {
            key "group-name";
            description
                "List for config data for access-circuit-group";
            leaf group-name  {
                type  leafref {
                    path  "../config/group-name";
                }
                description "Use this attribute to create a new access circuit group for MPLS";
            } // END of group-name definition.

            container config {
                description
                    "Configuration container for access circuit group";
                uses l2vpn-access-circuit-group-config;
            } // END of config-container definition.
            container state {
                config false;
                description
                    "Container for Operationa attributes for access circuit group";
                uses l2vpn-access-circuit-group-config;
            } // END of state-container definition.
        } // End of access-circuit-group-list
    } // END of l2vpn-access-circuit-group-top definition.
    grouping customer-service-map-top {
        description
            "Grouping for Operational attributes for service-template mapping";

        list map-list {
            key "vpls-name";
            config false;
            description
                "List for Operational data for Customer Service mapping";
            leaf vpls-name  {
                type  leafref {
                    path  "../state/vpls-name";
                }
                description "Use this attribute to retrieve confgiured VPLS instance details";
            } // END of vpls-name definition.

            container state {
                config false;
                description
                    "Operation state data for map-list";
                uses l2vpn-customer-service-map-state;
            } // END of state-container definition.
        } // End of map-list-list
    } // END of customer-service-map-top definition.
    grouping customer-service-template-config {
        description
            "Configuration attributes for customer-service-template";
        leaf name  {
            type  string {
                length "1..32";
                pattern "[a-zA-Z0-9_-]*";
            }
            description "Specify service template name";
        } // END of name definition.

        leaf match-all  {
            when " not(/ipi-mpls:mpls/ipi-mpls:l2vpn/ipi-mpls:customer-service-template/ipi-mpls:config/ipi-mpls:match-single-tag-outer-vlan-range) + not(/ipi-mpls:mpls/ipi-mpls:l2vpn/ipi-mpls:customer-service-template/ipi-mpls:config/ipi-mpls:match-untagged) + not(/ipi-mpls:mpls/ipi-mpls:l2vpn/ipi-mpls:customer-service-template/ipi-mpls:double-tag/ipi-mpls:match-outer-vlan-id) ";
            type  empty;
            description "Use this attribute to specify match criteria as match all";
        } // END of match-all definition.

        leaf-list match-single-tag-outer-vlan-range  {
            when " not(/ipi-mpls:mpls/ipi-mpls:l2vpn/ipi-mpls:customer-service-template/ipi-mpls:config/ipi-mpls:match-all) ";
            type  string {
                length "1..4094";
                pattern "[^?' =,>]+";
            }
            description "Use this attribute to set match type with outer vlan value";
        } // END of match-single-tag-outer-vlan-range definition.

        leaf match-untagged  {
            when " not(/ipi-mpls:mpls/ipi-mpls:l2vpn/ipi-mpls:customer-service-template/ipi-mpls:config/ipi-mpls:match-all) ";
            type  empty;
            description "Use this attribute to specify match criteria as match untagged";
        } // END of match-untagged definition.

    } // END of customer-service-template-config definition.
    grouping customer-service-template-double-tag-top {
        description
            "Top level groupig for customer-service-template double-tag attributes";

        list double-tag {
        when " not(/ipi-mpls:mpls/ipi-mpls:l2vpn/ipi-mpls:customer-service-template/ipi-mpls:config/ipi-mpls:match-all) ";
            key "match-outer-vlan-id";
            description
                "Configuration for double-tag configurations";
            leaf match-outer-vlan-id  {
                type  leafref {
                    path  "../config/match-outer-vlan-id";
                }
                description "Specify outer vlan id for match double tag";
            } // END of match-outer-vlan-id definition.

            container config {
                description
                    "Configuration container for double-tag configurations";
                uses customer-service-template-double-tag-config;
            } // END of config-container definition.
            container state {
                config false;
                description
                    "Container for Operationa attributes for double-tag";
                uses customer-service-template-double-tag-config;
            } // END of state-container definition.
        } // End of double-tag-list
    } // END of customer-service-template-double-tag-top definition.
    grouping customer-service-template-double-tag-config {
        description
            "Grouping for double-tag attributes";
        leaf match-outer-vlan-id  {
            type  uint16 {
                 range "1..4094"  {
                    description "1..4094:Outer vid value";
                 }
            }
            description "Specify outer vlan id for match double tag";
        } // END of match-outer-vlan-id definition.

        leaf-list match-inner-vlan-id  {
            type  string {
                length "1..1965";
                pattern "[^?' =,>]+";
            }
            description "Specify inner vlan VID or range(VLAN ID 1-4094 or range: 2-5) for
                        match double tag";
        } // END of match-inner-vlan-id definition.

    } // END of customer-service-template-double-tag-config definition.
    grouping customer-service-template-action-type-top {
        description
            "Top level groupig for customer-service-template action-type attributes";

        list action-type {
            key "vlan-action-type";
            description
                "Configuration for action-type configurations";
            leaf vlan-action-type  {
                type  leafref {
                    path  "../config/vlan-action-type";
                }
                description "Specify rewrite ingress action type";
            } // END of vlan-action-type definition.

            container config {
                description
                    "Configuration container for action-type configurations";
                uses customer-service-template-action-type-config;
            } // END of config-container definition.
            container state {
                config false;
                description
                    "Container for Operationa attributes for action-type";
                uses customer-service-template-action-type-config;
            } // END of state-container definition.
        } // End of action-type-list
    } // END of customer-service-template-action-type-top definition.
    grouping customer-service-template-action-type-config {
        description
            "Grouping for action-type attributes";
        leaf vlan-action-type  {
            type  ipi-mpls-types:mpls_l2vpn_vlan_action_type_t;
            description "Specify rewrite ingress action type";
        } // END of vlan-action-type definition.

        leaf outer-vlan-identifier  {
            when " /ipi-mpls:mpls/ipi-mpls:l2vpn/ipi-mpls:customer-service-template/ipi-mpls:action-type/ipi-mpls:config/ipi-mpls:vlan-action-type != '1' ";
            type  uint16 {
                 range "1..4094"  {
                    description "1..4094:Vid range";
                 }
            }
            description "Spefiy vlan identifier for action types push and translate`";
        } // END of outer-vlan-identifier definition.

        leaf tag-protocol-identifier  {
            when " /ipi-mpls:mpls/ipi-mpls:l2vpn/ipi-mpls:customer-service-template/ipi-mpls:action-type/ipi-mpls:config/ipi-mpls:vlan-action-type != '2' ";
            type  ipi-mpls-types:mpls_svc_tpid_t;
            default "dot1.q";
            description "Specify tag protocol identofier for action types pop and translate";
        } // END of tag-protocol-identifier definition.

    } // END of customer-service-template-action-type-config definition.
    grouping l2vpn-service-template-top {
        description
            "Top level Grouping for service template";

        list customer-service-template {
            key "name";
            description
                "List for config data for Customer Service Templat";
            leaf name  {
                type  leafref {
                    path  "../config/name";
                }
                description "Specify service template name";
            } // END of name definition.

            container config {
                description
                    "Configuration container for Service-template configurations";
                uses customer-service-template-config;
            } // END of config-container definition.
            container state {
                config false;
                description
                    "Container for Operationa attributes for Service-template";
                uses customer-service-template-config;
            } // END of state-container definition.
            uses customer-service-template-double-tag-top;
            uses customer-service-template-action-type-top;
            uses customer-service-map-top;
        } // End of customer-service-template-list
    } // END of l2vpn-service-template-top definition.

    grouping  mpls-grouping {
    description
        "Top level container for MPLS, including configuration and state data";
    container mpls {
        description
            "Top level container for MPLS, including configuration and state data";

        list label-space {
            key "label-space-name";
            description
                "MPLS Label-Space Configurations";
            leaf label-space-name  {
                type  leafref {
                    path  "../config/label-space-name";
                }
                description "This attribute identifies the label space";
            } // END of label-space-name definition.


            list module-label-range {
                key "module-name";
                description
                    "MPLS Module Label Range Configurations";
                leaf module-name  {
                    type  leafref {
                        path  "../config/module-name";
                    }
                    description "Use this attribute to specify the protocol module for which label
                                range is specified";
                } // END of module-name definition.

                container config {
                    description
                        "Config container for MPLS Module Label Range configuration";
                    uses module-label-range-config;
                } // END of config-container definition.
                container state {
                    config false;
                    description
                        "Operational state data for MPLS Module Label Range";
                    uses module-label-range-config;
                } // END of state-container definition.
            } // End of module-label-range-list
            container config {
                description
                    "Config container for MPLS Label Space Configurations";
                uses label-space-config;
            } // END of config-container definition.
            container state {
                config false;
                description
                    "Operational state container for MPLS Label Space";
                uses label-space-config;
            } // END of state-container definition.
            container global-label-range {
                description
                    "MPLS Global Label Range Configurations";
                container config {
                    presence "Global Label Range is configured for the label space";
                    description
                        "Config Container for MPLS Global Label Range Configurations";
                    uses label-range-config;
                } // END of config-container definition.
                container state {
                    config false;
                    description
                        "Operational state container for MPLS Global Label Range";
                    uses label-range-config;
                } // END of state-container definition.
            } // END of global-label-range-container definition.
        } // End of label-space-list

        list admin-group {
            if-feature feature-list:HAVE_TE;
            key "name id";
            description
                "MPLS Administrative Group Configurations";
            leaf name  {
                type  leafref {
                    path  "../config/name";
                }
                description "Use this attribute to create a name-to-value binding for an
                            administrative group";
            } // END of name definition.

            leaf id  {
                type  leafref {
                    path  "../config/id";
                }
                description "identifier value for the administrative group";
            } // END of id definition.

            container config {
                description
                    "Config Container for MPLS Administrative Groups";
                uses mpls-admin-group-config;
            } // END of config-container definition.
            container state {
                config false;
                description
                    "State Contatiner for MPLS Administrative Groups";
                uses mpls-admin-group-config;
            } // END of state-container definition.
        } // End of admin-group-list

        list bandwidth-class {
            if-feature feature-list:HAVE_TE;
            key "name";
            description
                "MPLS Bandwidth Class Configurations";
            leaf name  {
                type  leafref {
                    path  "../config/name";
                }
                description "Use this attribute to create a new bandwidth class name. Using this
                            command changes the command mode to Bandwidth-class mode";
            } // END of name definition.

            container config {
                description
                    "Config Container for MPLS Bandwidth Class Configurations";
                uses mpls-bandwidth-class-config;
            } // END of config-container definition.
            container state {
                config false;
                description
                    "State Contatiner for MPLS Bandwidth Class Configurations";
                uses mpls-bandwidth-class-config;
            } // END of state-container definition.
            container properties {
                description
                    "Properties for Bandwidth Class with no DSTE";
                container config {
                    presence "To configure BC without DSTE";
                    description
                        "Config Container for Bandwidth Class without DSTE";
                    uses mpls-bandwidth-properties-config;
                } // END of config-container definition.
                container state {
                    config false;
                    description
                        "State Container for MPLS Bandwidth Class Without DSTE Configurations";
                    uses mpls-bandwidth-properties-config;
                } // END of state-container definition.
            } // END of properties-container definition.
        } // End of bandwidth-class-list
        container l2vpn {
            description
                "Top Level container for l2vpn objects";
            uses l2vpn-service-template-top;
            uses l2vpn-access-circuit-group-top;
        } // END of l2vpn-container definition.
        container global {
            description
                "MPLS global configuration";
            container config {
                description
                    "MPLS global configuration";
                uses mpls-global-config;
            } // END of config-container definition.
            container state {
                config false;
                description
                    "Global MPLS Operational state data";
                uses mpls-global-config;
            } // END of state-container definition.
            container graceful-restart {
                if-feature feature-list:HAVE_RESTART;
                config false;
                description
                    "Graceful restart clients";
                container rsvp {
                    config false;
                    description
                        "Name of the graceful-restart client";
                    container state {
                        config false;
                        description
                            "State of the graceful-restart client";
                        uses nsm-client-graceful-restart-state;
                    } // END of state-container definition.
                } // END of rsvp-container definition.
                container ldp {
                    config false;
                    description
                        "Name of the graceful-restart client";
                    container state {
                        config false;
                        description
                            "State of the graceful-restart client";
                        uses nsm-client-graceful-restart-state;
                    } // END of state-container definition.
                } // END of ldp-container definition.
            } // END of graceful-restart-container definition.
        } // END of global-container definition.
        container interfaces {
            description
                "mpls interface level configuration and state data";

            list interface {
                key "name";
                description
                    "List of MPLS enabled interfaces on the device.";
                leaf name  {
                    type  leafref {
                        path  "/ipi-interface:interfaces/ipi-interface:interface/ipi-interface:config/ipi-interface:name";
                    }
                    description "The textual name of the interface.";
                } // END of name definition.

                container label-switching {
                    when " /ipi-interface:interfaces/ipi-interface:interface/ipi-interface:config/ipi-interface:enable-switchport != '1' ";
                    // when " !ipi-if-aggregate:member-aggregation ";
                    description
                        "Label switching configuration";
                    container config {
                        presence "Enable label switching for interface";
                        description
                            "Label switching configuration";
                        uses mpls-interface-label-switching-config;
                    } // END of config-container definition.
                    container state {
                        config false;
                        description
                            "Operational state for Label switching configuration";
                        uses mpls-interface-label-switching-config;
                    } // END of state-container definition.
                } // END of label-switching-container definition.
                container mpls-interface-bandwidth {
                    when " not(/ipi-interface:interfaces/ipi-interface:interface/ipi-if-aggregate:member-aggregation) ";
                    description
                        "MPLS Interface Bandwidth Configurations";
                    container config {
                        description
                            "Configurations for MPLS Interface Bandwidth";
                        uses mpls-interface-bandwidth-config;
                    } // END of config-container definition.
                    container state {
                        config false;
                        description
                            "Operational state for MPLS Interface Bandwidth";
                        uses mpls-interface-bandwidth-config;
                    } // END of state-container definition.
                } // END of mpls-interface-bandwidth-container definition.
            } // End of interface-list
        } // END of interfaces-container definition.
        container debug {
            if-feature feature-list:HAVE_MPLS_FWD;
            description
                "mpls debug level configuration and state data";
            container config {
                description
                    "mpls debug level configuration";
                uses mpls-debug-config;
            } // END of config-container definition.
            container state {
                config false;
                description
                    "Operational state data for MPLS Debug";
                uses mpls-debug-config;
            } // END of state-container definition.
        } // END of debug-container definition.
        container tunnel-policies {
            if-feature feature-list:HAVE_MPLS_SERVICE_MAPPING;
            description
                "tunnel policy configuration and state data";

            list tunnel-policy {
                key "name";
                description
                    "List of tunnel policies";
                leaf name  {
                    type  leafref {
                        path  "../config/name";
                    }
                    description "Name for the tunnel policy";
                } // END of name definition.

                container config {
                    description
                        "configuration for tunnel-policy";
                    uses tunnel-policies-config;
                } // END of config-container definition.
                container state {
                    config false;
                    description
                        "state data for tunnel policy";
                    uses tunnel-policies-config;
                } // END of state-container definition.
            } // End of tunnel-policy-list
        } // END of tunnel-policies-container definition.
        container six-pe-tunnel-policies {
            if-feature feature-list:HAVE_MPLS_SERVICE_MAPPING;
            description
                "6PE tunnel policy configuration and state data";

            list six-pe-tunnel-policy {
                key "name";
                max-elements 1;
                description
                    "List of tunnel policies";
                leaf name  {
                    type  leafref {
                        path  "../config/name";
                    }
                    description "Name for the tunnel policy";
                } // END of name definition.

                container config {
                    description
                        "configuration for tunnel selection policy";
                    uses mpls-6pe-tunnel-policy;
                } // END of config-container definition.
                container state {
                    config false;
                    description
                        "state data for 6PE tunnel policy";
                    uses mpls-6pe-tunnel-policy;
                } // END of state-container definition.
            } // End of six-pe-tunnel-policy-list
        } // END of six-pe-tunnel-policies-container definition.
    } // END of mpls-container definition.
    } // END of mpls-grouping definition.

    uses mpls-grouping;

}

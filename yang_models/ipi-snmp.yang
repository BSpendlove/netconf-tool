/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-snmp.yang
*
*/

module ipi-snmp {

    yang-version 1.1;

    namespace   "http://www.ipinfusion.com/yang/ocnos/ipi-snmp";

    prefix "ipi-snmp";

    import ipi-snmp-types {
        prefix ipi-snmp-types;
        revision-date 2021-07-28;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "Top level SNMP configuration module";


    revision "2021-07-28" {
        description "Initial Version";
        reference " 0.1.0.";
    }

    grouping snmp-server-trap-config {
        description
            "Grouping for snmp-server trap config objects.";
        leaf-list enable-traps  {
            type  ipi-snmp-types:snmp_trap_protocols;
            description "Use this attribute to enable or disable SNMP traps and inform
                        requests.";
        } // END of enable-traps definition.

        leaf enable-link-down-trap  {
            type  boolean;
            description "Use this attribute to enable or disable SNMP linkdown traps.";
        } // END of enable-link-down-trap definition.

        leaf enable-link-up-trap  {
            type  boolean;
            description "Use this attribute to enable or disable SNMP linkup traps.";
        } // END of enable-link-up-trap definition.

    } // END of snmp-server-trap-config definition.

    grouping  snmp-grouping {
    description
        "Top level container for snmp configuration common for all modules";
    container snmp {
        if-feature feature-list:HAVE_SNMP_AGENT;
        description
            "Top level container for snmp configuration common for all modules";
        container server-traps {
            description
                "Top level container for snmp-server trap configuration common for all
                        modules";
            container config {
                description
                    "This container defines snmp-server traps configuration.";
                uses snmp-server-trap-config;
            } // END of config-container definition.
            container state {
                config false;
                description
                    "This container defines snmp-server traps Operational states.";
                uses snmp-server-trap-config;
            } // END of state-container definition.
        } // END of server-traps-container definition.
    } // END of snmp-container definition.
    } // END of snmp-grouping definition.

    uses snmp-grouping;

    rpc snmp-agentx-enable-terminal-debugging {
        description "Use this attribute to enable agentx debug options.";
        input  {
            leaf debug  {
                type ipi-snmp-types:snmp_agentx_debug_type_t;
                mandatory true;
                description "Use this attribute to enable agentx debug options.";
            }
        }
    }

    rpc snmp-agentx-disable-terminal-debugging {
        description "Use this attribute to disable agentx debug options.";
        input  {
            leaf debug  {
                type ipi-snmp-types:snmp_agentx_debug_type_t;
                mandatory true;
                description "Use this attribute to disable agentx debug options.";
            }
        }
    }

}

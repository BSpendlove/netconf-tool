/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-if-aggregate.yang
*
*/

module ipi-if-aggregate {

    yang-version 1.1;

    namespace   "http://www.ipinfusion.com/yang/ocnos/ipi-if-aggregate";

    prefix "ipi-if-aggregate";

    import ipi-lag-types {
        prefix ipi-lag-types;
        revision-date 2021-09-03;
    }

    import ipi-interface {
        prefix ipi-interface;
        revision-date 2022-04-05;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "Interface level configurations for LAG";


    revision "2022-04-20" {
        description "Added changes for port channel weight";
        reference " 0.4.0.";
    }

    revision "2021-09-03" {
        description "Update descriptions of attribute";
        reference " 0.3.0.";
    }

    revision "2020-12-15" {
        description "Change to have data-types in lower case instead of camel case";
        reference " 0.2.0.";
    }

    revision "2018-06-21" {
        description "Initial Version";
        reference " 0.1.0.";
    }

    grouping port-channel-weight-config {
        description
            "Configuration data for port channel weight";
        leaf weight  {
            type  uint16 {
                 range "1..16"  {
                    description "1..16:port channel weight";
                 }
            }
            description "Set the port channel weight";
        } // END of weight definition.

    } // END of port-channel-weight-config definition.
    grouping aggregated-interface-config {
        description
            "Aggregated configuration data attributes group";
        leaf agg-type  {
            type  ipi-lag-types:lag_link_agg_type_t;
            mandatory true;
            description "Sets the type of LAG, how it is configured / maintained";
        } // END of agg-type definition.

        leaf aggregate-id  {
            type  uint16 {
                 range "1..16383"  {
                    description "1..16383:Specify a port-channel number";
                 }
            }
            mandatory true;
            description "Channel group identifier";
        } // END of aggregate-id definition.

        leaf lacp-mode  {
            type  ipi-lag-types:lacp_mode_t;
            mandatory true;
            description "Use this command to add a port to a channel group specified by the
                        channel group number (1-12). This command enables link aggregation on
                        a port, so that it may be selected for aggregation by the local
                        system.";
        } // END of lacp-mode definition.

    } // END of aggregated-interface-config definition.
    grouping aggregator-interface-config {
        description
            "Aggregator configuration data attributes group";
        leaf load-balance-criteria  {
            if-feature feature-list:HAVE_SWFWDR;
            if-feature feature-list:HAVE_LACP;
            type  ipi-lag-types:lag_load_balancing_criteria_t;
            description "Use this attribute to configure LACP port-channel load-balancing and
                        set port selection criteria (PSC) on an aggregator.";
        } // END of load-balance-criteria definition.

        leaf min-links  {
            if-feature feature-list:HAVE_LACP;
            type  uint8 {
                 range "2..32"  {
                    description "2..32:Minimum links number";
                 }
            }
            description "Minimum number of active links required in this aggregator";
        } // END of min-links definition.

        leaf min-bandwidth  {
            if-feature feature-list:HAVE_LACP;
            type  string {
                length "1..1965";
                pattern "[^?' =,>|]+";
            }
            description "";
        } // END of min-bandwidth definition.

    } // END of aggregator-interface-config definition.
    grouping aggregator-interface-state {
        description
            "Aggregator interface operational data";
        leaf agg-min-links-state  {
            type  ipi-lag-types:lag_agg_min_links_status;
            config false;
            description "Aggregator is 'up' if 'min-links' number of active links in
                        aggregator, else 'down'";
        } // END of agg-min-links-state definition.

    } // END of aggregator-interface-state definition.

    grouping  member-aggregation-grouping {
    description
        "NSM LACP interface related operations";
    container member-aggregation {
        description
            "NSM LACP interface related operations";
        container config {
            presence "yes";
            description
                "Configuration data for aggregated inerface level";
            uses aggregated-interface-config;
        } // END of config-container definition.
        container state {
            config false;
            description
                "Operation state data for static/lacp aggregators";
            uses aggregated-interface-config;
        } // END of state-container definition.
        container port-channel-weight {
            if-feature feature-list:HAVE_DUNE;
            description
                "configure port channel weight";
            container config {
                description
                    "Configuration data for port channel weight";
                uses port-channel-weight-config;
            } // END of config-container definition.
            container state {
                config false;
                description
                    "Operation state data for port channel weight";
                uses port-channel-weight-config;
            } // END of state-container definition.
        } // END of port-channel-weight-container definition.
    } // END of member-aggregation-container definition.
    } // END of member-aggregation-grouping definition.

    grouping  aggregator-grouping {
    description
        "NSM LACP aggregator related operations";
    container aggregator {
        presence "yes";
        description
            "NSM LACP aggregator related operations";
        container config {
            description
                "Configuration data for aggregator inerfaced";
            uses aggregator-interface-config;
        } // END of config-container definition.
        container state {
            config false;
            description
                "Operational data for static/lacp aggregators";
            uses aggregator-interface-config;
            uses aggregator-interface-state;
        } // END of state-container definition.
    } // END of aggregator-container definition.
    } // END of aggregator-grouping definition.

    augment /ipi-interface:interfaces/ipi-interface:interface {
    when " /ipi-interface:interfaces/ipi-interface:interface/ipi-interface:name ";
        description
            "NSM LACP interface related operations";
        uses member-aggregation-grouping;
    }

    augment /ipi-interface:interfaces/ipi-interface:interface {
        description
            "NSM LACP aggregator related operations";
        uses aggregator-grouping;
    }


    notification agg-min-links-state-update {

        description "Notify when a total Active (link-UP) LAG member count becomes less than the configured min-link count. Severity level is CRITICAL for interface going down and INFO for interface moving to UP state..";

        // eventClass "STATE";
        leaf name {
            type  string;
        description
            "The textual name of the interface. The value of this
                    object should
                    be the name of the interface as assigned by the local device and
                    should be suitable for use in commands entered at the device's
                    `console'. This might be a text name, such as `le0' or a simple
                    port number, such as `1', depending on the interface naming syntax
                    of the device. If several entries in the ifTable together represent
                    a single interface as named by the device, then each will have the
                    same value of name. Note that for an agent which responds to SNMP
                    queries concerning an interface on some other (proxied) device,
                    then the value of name for such an interface is the proxied
                    device's local name for it. If there is no local name, or this
                    object is otherwise not applicable, then this object contains a
                    zero-length string.";
        }

        leaf agg-min-links-state {
            type ipi-lag-types:lag_agg_min_links_status;
        description
            "Aggregator is 'up' if 'min-links' number of active links in
                    aggregator, else 'down'";
        }
    }

}

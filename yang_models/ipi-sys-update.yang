/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-sys-update.yang
*
*/

module ipi-sys-update {

    yang-version 1.1;

    namespace   "http://www.ipinfusion.com/yang/ocnos/ipi-sys-update";

    prefix "ipi-sys-update";

    organization
        "IP Infusion Inc.";

    contact
        "Address: 3965 Freedom Circle, Suite 200, Santa Clara, CA 95054
         Phone: +1 408-400-1900
         E-mail: support@ipinfusion.com
         Web: http://www.ipinfusion.com/";

    description
        "sys-update provides the possibility for users to upgrade/downgrade
                OcNOS image in a router";


    revision "2021-07-30" {
        description "sys-update restructured";
        reference "Initial Version";
    }

    grouping system-update-state {
        description
            "systemCMLSEPupdateCMLSEPstate";
        leaf name  {
            type  string {
                length "1..1965";
                pattern "[^?' =,>|]+";
            }
            description "Installer image available in the device.";
        } // END of name definition.

    } // END of system-update-state definition.
    grouping system-update-top {
        description
            "systemCMLSEPupdateCMLSEPtop";
        container installers {
            config false;
            description
                "Container for system-update installers";

            list installer {
                key "name";
                config false;
                description
                    "List of installers";
                leaf name  {
                    type  leafref {
                        path  "../state/name";
                    }
                    description "Installer image available in the device.";
                } // END of name definition.

                container state {
                    config false;
                    description
                        "Installer operational data";
                    uses system-update-state;
                } // END of state-container definition.
            } // End of installer-list
        } // END of installers-container definition.
    } // END of system-update-top definition.

    grouping  system-update-grouping {
    description
        "Container for system-update";
    container system-update {
        description
            "Container for system-update";
        uses system-update-top;
    } // END of system-update-container definition.
    } // END of system-update-grouping definition.

    uses system-update-grouping;

    rpc sys-update-install {
        description "Use this RPC to upgrade current software to a newer/older version.
                    Device will restore the startup configuration post upgrade, so to save
                    the running configuration into startup configuration perform
                    copy-config operation before sys-update operation. When device doesn't
                    have valid license this operation cannot performed. To download the
                    installer image management interface is used when source-interface
                    attribute is not specified";
        input  {
            leaf installer-name  {
                type string;
                mandatory true;
                description "Installer filename";
            }
            leaf ignore-feature-check  {
                type boolean;
                mandatory true;
                description "Ignore license feature check";
            }
        }
    }

    rpc sys-update-uninstall {
        description "Use this RPC to uninstall device software";
        reference "None";
    }

    rpc sys-update-get {
        description "Use this RPC to download an installer image.";
        input  {
            leaf source-interface  {
                type string;
                mandatory true;
                description "Source interface";
            }
            leaf url  {
                type string;
                mandatory true;
                description "Installer URL";
            }
        }
    }

    rpc sys-update-delete {
        description "Use this RPC to delete a downloaded image.";
        input  {
            leaf image-name  {
                type string;
                mandatory true;
                description "Installer filename";
            }
        }
    }

    rpc sys-update-cancel-download {
        description "Use this RPC to cancel the download which is running in the
                    background.";
    }

    notification sys-update-installation-status {

        description "This system update event is generated when the software installation starts and ends..";

        // severity "INFO";
        // eventClass "MESSAGE";
        leaf message {
            type string;
            description " alarm message notification";
        }
    }

    notification sys-update-download-status {

        description "Notification sent on successful download operation with INFO severity or on failed download operation with MAJOR severity..";

        // severity "INFO";
        // eventClass "MESSAGE";
        leaf message {
            type string;
            description " alarm message notification";
        }
    }

}

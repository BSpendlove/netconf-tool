/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ras.yang
*
*/

module ipi-ras {

    yang-version 1.1;

    namespace   "http://www.ipinfusion.com/yang/ocnos/ipi-ras";

    prefix "ipi-ras";

    organization
        "IP Infusion Inc.";

    contact
        "Address: 3965 Freedom Circle, Suite 200, Santa Clara, CA 95054
         Phone: +1 408-400-1900
         E-mail: support@ipinfusion.com
         Web: http://www.ipinfusion.com/";

    description
        "HSL RAS Managed Object";


    revision "2021-12-07" {
        description "Restructured module as per open-config";
        reference " 0.2.0.";
    }

    revision "2018-06-21" {
        description "Initial Version";
        reference " 0.1.0.";
    }



    rpc platform-clear-hsl-ipc-stat-values {
        description "Clear HSL IPC stats values";
        input  {
            leaf start-value  {
                type uint16;
                mandatory true;
                description "Starting value for clear ipc-stat";
            }
            leaf end-value  {
                type uint16;
                mandatory true;
                description "Ending value for clear ipc-stat";
            }
        }
    }

    rpc platform-clear-hsl-ipc-stat {
        description "Clear HSL IPC stat";
    }

    rpc platform-clear-hsl-mlag-mac-sync {
        description "Clear HSL MLAG MAC Sync";
    }

    rpc platform-clear-hardware-discard-counters {
        description "Clear Hardware Discard counters";
    }

    rpc platform-clear-hsl-fdb-debug-counters {
        description "Clear HSL FDB Debug counters";
    }

}

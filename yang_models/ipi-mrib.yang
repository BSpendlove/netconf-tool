/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-mrib.yang
*
*/

module ipi-mrib {

    yang-version 1.1;

    namespace   "http://www.ipinfusion.com/yang/ocnos/ipi-mrib";

    prefix "ipi-mrib";

    import ipi-mrib-types {
        prefix ipi-mrib-types;
        revision-date 2021-12-02;
    }

    include ipi-mrib-ipv4 { revision-date 2021-12-02;}
    include ipi-mrib-common { revision-date 2022-04-22;}
    organization
        "IP Infusion Inc.";

    contact
        "Address: 3965 Freedom Circle, Suite 200, Santa Clara, CA 95054
         Phone: +1 408-400-1900
         E-mail: support@ipinfusion.com
         Web: http://www.ipinfusion.com/";

    description
        "Datamodel for MRIB object";


    revision "2022-04-22" {
        description "Suncom patch merge";
        reference " 0.2.1.";
    }

    revision "2021-12-02" {
        description "Restructured module as per open-config style";
        reference " 0.2.0.";
    }

    revision "2018-06-21" {
        description "Initial Version";
        reference " 0.1.0.";
    }


    grouping  mrib-grouping {
    description
        "Top level container for all multicast RIB configuration and state data";
    container mrib {
        description
            "Top level container for all multicast RIB configuration and state data";
        uses ipv4-grouping;
    } // END of mrib-container definition.
    } // END of mrib-grouping definition.

    uses mrib-grouping;

    rpc mrib-ipv4-terminal-debugging-on {
        description "RPC to enable IPv4 MRIB terminal debug options";
        input  {
            leaf vrf-name  {
                type string;
                description "vrf name";
            }
            leaf term-debug-options  {
                type ipi-mrib-types:mrib_debug_t;
                mandatory true;
                description "Enable IP MRIB debug options";
            }
        }
    }

    rpc mrib-ipv4-terminal-debugging-off {
        description "RPC to disable IPv4 MRIB terminal debug options";
        input  {
            leaf vrf-name  {
                type string;
                description "vrf name";
            }
            leaf term-debug-options  {
                type ipi-mrib-types:mrib_debug_t;
                mandatory true;
                description "Disable IP MRIB debug options";
            }
        }
    }

}

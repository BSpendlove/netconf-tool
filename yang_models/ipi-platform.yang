/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-platform.yang
*
*/

module ipi-platform {

    yang-version 1.1;

    namespace   "http://www.ipinfusion.com/yang/ocnos/ipi-platform";

    prefix "ipi-platform";

    import ipi-interface {
        prefix ipi-interface;
        revision-date 2022-04-05;
    }

    import ipi-platform-types {
        prefix ipi-platform-types;
        revision-date 2022-02-17;
    }

    import ipi-platform-transceiver-types {
        prefix ipi-platform-transceiver-types;
        revision-date 2021-09-03;
    }

    import ietf-yang-types {
        prefix yang;
        revision-date 2013-07-15;
    }

    import cml-data-types {
        prefix cml-data-types;
        revision-date 2022-04-04;
    }

    import feature-list {
        prefix feature-list;
        revision-date 2022-07-13;
    }

    include ipi-platform-temperature { revision-date 2021-09-03;}
    include ipi-platform-cpu { revision-date 2021-09-03;}
    include ipi-platform-storage { revision-date 2021-09-03;}
    include ipi-platform-ram { revision-date 2021-09-03;}
    include ipi-platform-transceiver { revision-date 2022-02-18;}
    include ipi-platform-power-supply { revision-date 2021-09-03;}
    include ipi-platform-fan { revision-date 2021-09-03;}
    include ipi-platform-fan-tray { revision-date 2021-09-03;}
    include ipi-platform-chassis { revision-date 2021-12-10;}
    include ipi-platform-linecard { revision-date 2021-09-03;}
    include ipi-platform-power-rail { revision-date 2021-09-03;}
    include ipi-platform-poe { revision-date 2021-12-20;}
    include ipi-platform-profile { revision-date 2022-01-07;}
    include ipi-platform-profile-extended { revision-date 2022-01-21;}
    organization
        "IP Infusion Inc.";

    contact
        "Address: 3965 Freedom Circle, Suite 200, Santa Clara, CA 95054
         Phone: +1 408-400-1900
         E-mail: support@ipinfusion.com
         Web: http://www.ipinfusion.com/";

    description
        "This module defines a data model for representing a system
                component inventory, which can include hardware or software
                elements arranged in an arbitrary structure. The primary
                relationship supported by the model is containment, e.g.,
                components containing subcomponents.";


    revision "2022-02-18" {
        description "Updated ipi-platform-transceiver submodule";
        reference " 0.12.12.";
    }

    revision "2022-01-21" {
        description "Added when tag to all load-balance child containers on ipi-platfomr-extended sumodule";
        reference " 0.12.10.";
    }

    revision "2022-01-11" {
        description "Added when tag to inner-ipv4 non-symmetric on ipi-platform-profile-extended submodule";
        reference " 0.12.9.";
    }

    revision "2022-01-07" {
        description "Changed cpu-q-default from attribute to rpc on platform-profile";
        reference " 0.12.8.";
    }

    revision "2022-01-06" {
        description "Added new attribute hardware-profile port-config";
        reference " 0.12.7.";
    }

    revision "2022-01-03" {
        description "Added implicit-delete to load-balance config on ipi-platform-profile";
        reference " 0.12.6.";
    }

    revision "2021-12-30" {
        description "Removed autoPopulate tag from platform container on ipi-platform-profile-extended";
        reference " 0.12.5.";
    }

    revision "2021-12-27" {
        description "Added when tag to mpls-ler container on ipi-platform-profile-extended";
        reference " 0.12.4.";
    }

    revision "2021-12-20" {
        description "Introduced new sub-module ipi-platform-poe.";
        reference " 0.12.3.";
    }

    revision "2021-12-10" {
        description "Changed datatype of system status attributes";
        reference " 0.12.2.";
    }

    revision "2021-11-22" {
        description "Updated ipi-platform-profile submodule with DNX Broadcom platform hardware profiles";
        reference " 0.12.1.";
    }

    revision "2021-11-16" {
        description "Added new attributes for disk activity monitoring ";
        reference " 0.12.0.";
    }

    revision "2021-10-12" {
        description "Updated ipi-platform-profile submodule";
        reference " 0.11.1.";
    }

    revision "2021-09-06" {
        description "Updated ipi-platform-profile submodule";
        reference " 0.11.0.";
    }

    revision "2021-08-19" {
        description "Updated ipi-platform-transceiver submodule";
        reference " 0.10.9.";
    }

    revision "2021-08-16" {
        description "Updated submodule ipi-platform-transceiver with new attributes and notifications";
        reference " 0.10.8.";
    }

    revision "2021-08-13" {
        description "Notifications added for submodules ipi-platform-transceiver and ipi-platform-storage.";
        reference " 0.10.7.";
    }

    revision "2021-07-29" {
        description "Updated submodule ipi-platform-profile with new filter type ipsg and ipsg-ipv6 group.";
        reference " 0.10.6.";
    }

    revision "2021-07-28" {
        description "Updated submodule ipi-platform-profile for non-DNX Broadcom platform.";
        reference " 0.10.5.";
    }

    revision "2021-07-21" {
        description "New attributes added for submodule ipi-platform-power-rail";
        reference " 0.10.4.";
    }

    revision "2021-07-07" {
        description "Removed pattern from string attributes for submodule ipi-platform-transceiver";
        reference " 0.10.3.";
    }

    revision "2021-06-29" {
        description "Updated submodule ipi-platform-profile for new attribute ingress-ipv6-acl.";
        reference " 0.10.2.";
    }

    revision "2021-06-25" {
        description "Updated submodule ipi-platform-profile with new filter type dhcp-snoop and dhcp-snoop-ipv6 group.";
        reference " 0.10.1.";
    }

    revision "2021-06-24" {
        description "New Types added, submodule ipi-platform-port added and submodules ipi-platform-storage, ipi-platform-temperature, ipi-platform-transceiver, ipi-platform-transceiver-types, ipi-platform-types, ipi-transport-line-common changed.";
        reference " 0.10.0.";
    }

    revision "2021-06-23" {
        description "Updated submodule ipi-platform-profile for attribute ingress-bfd datatype changed.";
        reference " 0.9.2.";
    }

    revision "2021-06-17" {
        description "Updated submodule ipi-platform-profile for non-DNX Broadcom platform.";
        reference " 0.9.1.";
    }

    revision "2021-06-11" {
        description "Some BMC sensor attributes had the type changes from two decimal places to three.";
        reference " 0.9.0.";
    }

    revision "2021-05-31" {
        description "New attributes added for submodule ipi-platform-storage";
        reference " 0.8.0.";
    }

    revision "2021-04-28" {
        description "Submodule ipi-platform-cpu changed.";
        reference " 0.7.0.";
    }

    revision "2021-03-30" {
        description "Introduced new sub-modules ipi-platform-profile.";
        reference " 0.6.0.";
    }

    revision "2021-03-18" {
        description "Updated ipi-platform-power-supply sub-module. Removed pattern from string attributes.";
        reference " 0.5.0.";
    }

    revision "2021-01-25" {
        description "Introduced new sub-modules ipi-platform-temperature, ipi-platform-power-supply, ipi-fan, ipi-fan-tray, ipi-chassis, ipi-linecard, and ipi-power-rail. Fixed attribute transceiver-code typo.";
        reference " 0.4.0.";
    }

    revision "2021-01-18" {
        description "Introduced new ipi-platform-cpu sub-module";
        reference " 0.3.0.";
    }

    revision "2020-12-15" {
        description "Change to have data-types in lower case instead of camel case";
        reference " 0.2.0.";
    }

    revision "2018-06-21" {
        description "Initial Version";
        reference " 0.1.0.";
    }

    grouping component-memory-state-detail {
        description
            "Per-component memory statistics detail";
        leaf available  {
            type  uint64;
            units "Mbytes";
            description "The available memory physically installed, or logically allocated to
                        the component.";
        } // END of available definition.

        leaf utilized  {
            type  uint64;
            units "Mbytes";
            description "utilized memory.";
        } // END of utilized definition.

    } // END of component-memory-state-detail definition.
    grouping component-board-state-detail {
        description
            "Per-component board detail";
        leaf board-name  {
            type  string {
                length "1..1965";
            }
            description "Name of the Board";
        } // END of board-name definition.

        leaf board-serial-no  {
            type  string {
                length "1..1965";
            }
            description "Serial No of the device";
        } // END of board-serial-no definition.

        leaf board-mfg-name  {
            type  string {
                length "1..1965";
            }
            description "Device's manufacturer name";
        } // END of board-mfg-name definition.

        leaf board-mfg-date  {
            type  yang:date-and-time {
                pattern "\\d{4}-\\d{2}-\\d{2}T\\d{2}:\\d{2}:\\d{2}(\\.\\d+)?(Z|[\\+\\-]\\d{2}:\\d{2})";
                }
                description "Device's manufacturing date.";
            } // END of board-mfg-date definition.

    } // END of component-board-state-detail definition.
    grouping system-load {
        description
            "System load group";
        leaf system-1min-load-avg-warning-threshold  {
            type  uint8 {
                 range "41..100"  {
                    description "41..100:41-100";
                 }
            }
            description "System 1min average load threshold for warning";
        } // END of system-1min-load-avg-warning-threshold definition.

        leaf system-1min-load-avg-alarm  {
            type  uint8 {
                 range "51..100"  {
                    description "51..100:51-100";
                 }
            }
            description "System 1min average load for alarm";
        } // END of system-1min-load-avg-alarm definition.

        leaf system-5min-load-avg-alarm  {
            type  uint8 {
                 range "51..100"  {
                    description "51..100:51-100";
                 }
            }
            description "System 5min average load for alarm";
        } // END of system-5min-load-avg-alarm definition.

        leaf system-15min-load-avg-alarm  {
            type  uint8 {
                 range "51..100"  {
                    description "51..100:51-100";
                 }
            }
            description "System 15min average load for alarm";
        } // END of system-15min-load-avg-alarm definition.

    } // END of system-load definition.
    grouping cpu-threshold {
        description
            "cpu threshold group";
        leaf warning-threshold  {
            type  uint8 {
                 range "51..100"  {
                    description "51..100:51-100";
                 }
            }
            description "Cpu threshold for warning";
        } // END of warning-threshold definition.

        leaf alarm-threshold  {
            type  uint8 {
                 range "91..100"  {
                    description "91..100:91-100";
                 }
            }
            description "Cpu threshold for alarm";
        } // END of alarm-threshold definition.

    } // END of cpu-threshold definition.
    grouping component-generic-global {
        description
            "Generic platform global configuration";
        leaf warning-repeat  {
            type  empty;
            description "To enable cmm warning level logs to repeat.";
        } // END of warning-repeat definition.

    } // END of component-generic-global definition.
    grouping system-load-cpu-usage-global {
        description
            "System load and CPU usage global group";

        list system-load-average-threshold {
            key "system-1min-load-avg-warning-threshold system-1min-load-avg-alarm system-5min-load-avg-alarm system-15min-load-avg-alarm";
            max-elements 1;
            description
                "Global system load average";
            leaf system-1min-load-avg-warning-threshold  {
                type  leafref {
                    path  "../config/system-1min-load-avg-warning-threshold";
                }
                description "System 1min average load threshold for warning";
            } // END of system-1min-load-avg-warning-threshold definition.

            leaf system-1min-load-avg-alarm  {
                type  leafref {
                    path  "../config/system-1min-load-avg-alarm";
                }
                description "System 1min average load for alarm";
            } // END of system-1min-load-avg-alarm definition.

            leaf system-5min-load-avg-alarm  {
                type  leafref {
                    path  "../config/system-5min-load-avg-alarm";
                }
                description "System 5min average load for alarm";
            } // END of system-5min-load-avg-alarm definition.

            leaf system-15min-load-avg-alarm  {
                type  leafref {
                    path  "../config/system-15min-load-avg-alarm";
                }
                description "System 15min average load for alarm";
            } // END of system-15min-load-avg-alarm definition.

            container config {
                description
                    "system level load configuration";
                uses system-load;
            } // END of config-container definition.
            container state {
                config false;
                description
                    "system level load operational data";
                uses system-load;
                uses temperature-grouping;
            } // END of state-container definition.
        } // End of system-load-average-threshold-list

        list cpu-core-usage-threshold {
            key "warning-threshold alarm-threshold";
            max-elements 1;
            description
                "Global level cpu usage threshold";
            leaf warning-threshold  {
                type  leafref {
                    path  "../config/warning-threshold";
                }
                description "Cpu threshold for warning";
            } // END of warning-threshold definition.

            leaf alarm-threshold  {
                type  leafref {
                    path  "../config/alarm-threshold";
                }
                description "Cpu threshold for alarm";
            } // END of alarm-threshold definition.

            container config {
                description
                    "Global level cpu threshold configuration";
                uses cpu-threshold;
            } // END of config-container definition.
            container state {
                config false;
                description
                    "system level load operational data";
                uses cpu-threshold;
                uses temperature-grouping;
            } // END of state-container definition.
        } // End of cpu-core-usage-threshold-list
    } // END of system-load-cpu-usage-global definition.
    grouping component-interface {
        description
            "interface configuration group";
        leaf monitor-port  {
            type  ipi-platform-types:cmm_monitor_state;
            description "To enable DDM monitor for current transceiver.";
        } // END of monitor-port definition.

        leaf poe-enable  {
            type  empty;
            description "To enable PoE for current interface.";
        } // END of poe-enable definition.

        leaf videopiu-port  {
            if-feature feature-list:HAVE_VPIU_EMULATION;
            type  ipi-platform-types:cmm_videopiu_state;
            description "To enable VIDEO PIU for current transceiver.";
        } // END of videopiu-port definition.

        leaf transceiver-code  {
            type  ipi-platform-transceiver-types:ddm_transceiver_t;
            description "To set transceiver code for current transceiver.";
        } // END of transceiver-code definition.

        leaf wavelength  {
            type  ipi-platform-types:cml_wavelength_t;
            description "wavelength";
        } // END of wavelength definition.

        leaf tx-disable  {
            type  empty;
            description "To disable laser tx for current transceiver.";
        } // END of tx-disable definition.

    } // END of component-interface definition.
    grouping platform-component-interface-list {
        description
            "global interface configuration list group";

        list interface {
            key "interface-name";
            description
                "Platform interface related operations";
            leaf interface-name  {
                type  leafref {
                    path  "/ipi-interface:interfaces/ipi-interface:interface/ipi-interface:name";
                }
                description "Use this attribute to perform platform's interface related
                            configurations";
            } // END of interface-name definition.

            container config {
                description
                    "interface related configurations";
                uses component-interface;
            } // END of config-container definition.
            container state {
                config false;
                description
                    "Operational data for interface";
                uses component-interface;
                uses temperature-grouping;
            } // END of state-container definition.
        } // End of interface-list
    } // END of platform-component-interface-list definition.
    grouping component-generic-debug {
        description
            "Grouping debug info for generic platform";
        leaf cmm-debug-enable  {
            type  empty;
            description "Use this attribute to turn on debugging for chassis monitoring";
        } // END of cmm-debug-enable definition.

    } // END of component-generic-debug definition.
    grouping component-generic-terminal-debug {
        description
            "Grouping terminal debug info for generic platform";
        leaf cmm-terminal-debug  {
            type  empty;
            description "Use this attribute to see the terminal debugging state for chassis
                        monitoring";
        } // END of cmm-terminal-debug definition.

    } // END of component-generic-terminal-debug definition.
    grouping component-bmc-sensor-record-state {
        description
            "componentCMLSEPbmcCMLSEPsensorCMLSEPrecordCMLSEPstate";
        container state {
            config false;
            description
                "Operational data for bmc-sensor";
            leaf sensor-name  {
                type  string {
                    length "1..1965";
                }
                description "sensor name";
            } // END of sensor-name definition.

            leaf value  {
                type  ipi-platform-types:cmm_bmc_value_t;
                description "sensor record value.Value -100002 represents not applicable";
            } // END of value definition.

            leaf units  {
                type  string {
                    length "1..1965";
                }
                description "unit of sensor record";
            } // END of units definition.

            leaf lower-non-recoverable  {
                type  decimal64 {
                     fraction-digits 3;                }
                description "lower non recoverable sensor threshold.-100002 represents not
                            applicable";
            } // END of lower-non-recoverable definition.

            leaf lower-non-critical  {
                type  decimal64 {
                     fraction-digits 3;                }
                description "lower non critical sensor threshold.-100002 represents not applicable";
            } // END of lower-non-critical definition.

            leaf lower-critical  {
                type  decimal64 {
                     fraction-digits 3;                }
                description "lower non critical sensor threshold.-100002 represents not applicable";
            } // END of lower-critical definition.

            leaf upper-non-critical  {
                type  decimal64 {
                     fraction-digits 3;                }
                description "upper non critical sensor threshold.-100002 represents not applicable";
            } // END of upper-non-critical definition.

            leaf upper-critical  {
                type  decimal64 {
                     fraction-digits 3;                }
                description "upper critical sensor threshold.-100002 represents not applicable";
            } // END of upper-critical definition.

            leaf upper-non-recoverable  {
                type  decimal64 {
                     fraction-digits 3;                }
                description "upper critical sensor threshold.-100002 represents not applicable";
            } // END of upper-non-recoverable definition.

            leaf operational-status  {
                type  string {
                    length "1..1965";
                }
                description "Sensor's operational state";
            } // END of operational-status definition.

            leaf threshold  {
                type  decimal64 {
                     fraction-digits 3;                }
                description "threshold for sensor notification";
            } // END of threshold definition.

            leaf event-type  {
                type  ipi-platform-types:cmm_bmc_event_type_t;
                description "Type of event for sensor notification";
            } // END of event-type definition.

            uses temperature-grouping;
        } // END of state-container definition.
    } // END of component-bmc-sensor-record-state definition.
    grouping component-hardware-debug {
        description
            "Grouping debug info for hardware related debug";
        leaf ddm-debug-enable  {
            if-feature feature-list:NOT_HAVE_TIBIT;
            type  empty;
            description "Use this attribute to turn on debugging for digital diagnostic
                        monitoring";
        } // END of ddm-debug-enable definition.

    } // END of component-hardware-debug definition.
    grouping component-hardware-terminal-debug {
        description
            "Grouping terminal hardware related debug";
        leaf ddm-terminal-debug  {
            if-feature feature-list:NOT_HAVE_TIBIT;
            type  empty;
            description "Use this attribute to see the debugging state for digital diagnostic
                        monitoring";
        } // END of ddm-terminal-debug definition.

    } // END of component-hardware-terminal-debug definition.
    grouping platform-component-state {
        description
            "Operational state data for device components";
        leaf type  {
            if-feature feature-list:NOT_HAVE_TIBIT;
            type  ipi-platform-types:cmm_component_type_t;
            description "Type of component as identified by the system";
        } // END of type definition.

        leaf location  {
            if-feature feature-list:NOT_HAVE_TIBIT;
            type  string {
                length "1..1965";
            }
            description "System-supplied description of the location of the
                        component within the system. This could be a bay position,
                        slot number, socket location, etc. For component types that
                        have an explicit slot-id attribute, such as linecards, the
                        system should populate the more specific slot-id.";
        } // END of location definition.

        leaf mfg-name  {
            if-feature feature-list:NOT_HAVE_TIBIT;
            type  string {
                length "1..1965";
            }
            description "System-supplied identifier for the manufacturer of the component.This
                        data is particularly useful when a component manufacturer is different
                        than the overall device vendor.";
        } // END of mfg-name definition.

        leaf mfg-date  {
            if-feature feature-list:NOT_HAVE_TIBIT;
            type  yang:date-and-time {
                pattern "\\d{4}-\\d{2}-\\d{2}T\\d{2}:\\d{2}:\\d{2}(\\.\\d+)?(Z|[\\+\\-]\\d{2}:\\d{2})";
                }
                description "System-supplied representation of the component's manufacturing date.";
            } // END of mfg-date definition.

            leaf description  {
                if-feature feature-list:NOT_HAVE_TIBIT;
                type  string {
                    length "1..1965";
                }
                description "System-supplied description of the component.";
            } // END of description definition.

            leaf hardware-version  {
                if-feature feature-list:NOT_HAVE_TIBIT;
                type  string {
                    length "1..1965";
                }
                description "For hardware components, this is the hardware revision of the
                            component.";
            } // END of hardware-version definition.

            leaf firmware-version  {
                if-feature feature-list:NOT_HAVE_TIBIT;
                type  string {
                    length "1..1965";
                }
                description "For hardware components, this is the version of associated firmware
                            that is running on the component, if applicable.";
            } // END of firmware-version definition.

            leaf software-version  {
                if-feature feature-list:NOT_HAVE_TIBIT;
                type  string {
                    length "1..1965";
                }
                description "For software components such as operating system or other software
                            module,this is the version of the currently running software.";
            } // END of software-version definition.

            leaf serial-no  {
                if-feature feature-list:NOT_HAVE_TIBIT;
                type  string {
                    length "1..1965";
                }
                description "System-assigned serial number of the component.";
            } // END of serial-no definition.

            leaf part-no  {
                if-feature feature-list:NOT_HAVE_TIBIT;
                type  string {
                    length "1..1965";
                }
                description "System-assigned part number for the component.This should be present
                            in particular if the component is also an FRU(field replaceable unit).";
            } // END of part-no definition.

            leaf removable  {
                if-feature feature-list:NOT_HAVE_TIBIT;
                type  boolean;
                description "If true,this component is removable or is a field replaceable unit";
            } // END of removable definition.

            leaf oper-status  {
                if-feature feature-list:NOT_HAVE_TIBIT;
                type  ipi-platform-types:cmm_component_oper_status_t;
                description "If applicable,this reports the current operational status of the
                            component.";
            } // END of oper-status definition.

            leaf product-name  {
                if-feature feature-list:NOT_HAVE_TIBIT;
                type  string {
                    length "1..1965";
                }
                description "Component's product name";
            } // END of product-name definition.

            leaf asset-tag  {
                if-feature feature-list:NOT_HAVE_TIBIT;
                type  string {
                    length "1..1965";
                }
                description "Component's asset tag";
            } // END of asset-tag definition.

            leaf-list component-additional-details  {
                if-feature feature-list:NOT_HAVE_TIBIT;
                type  string {
                    length "1..1965";
                    pattern "[^?' =,>|]+";
                }
                description "Component's extra details";
            } // END of component-additional-details definition.

            leaf parent  {
                if-feature feature-list:NOT_HAVE_TIBIT;
                type  leafref {
                    path  "/components/component/state/name";
                }
                description "Reference to the name of the parent component.";
            } // END of parent definition.

    } // END of platform-component-state definition.
    grouping platform-component-memory-state {
        description
            "Per-component memory statistics";
        container memory {
            if-feature feature-list:NOT_HAVE_TIBIT;
            config false;
            description
                "For components that have associated memory, these values
                        report information about available and utilized memory";
            uses component-memory-state-detail;
        } // END of memory-container definition.
    } // END of platform-component-memory-state definition.
    grouping platform-component-board-state {
        description
            "Per-component board state";
        container board-fru {
            if-feature feature-list:NOT_HAVE_TIBIT;
            config false;
            description
                "For components that have associated board fru details";
            uses component-board-state-detail;
        } // END of board-fru-container definition.
    } // END of platform-component-board-state definition.
    grouping component-hardware-global {
        description
            "Platform hardware global states";
        leaf locator-led-enable  {
            if-feature feature-list:NOT_HAVE_TIBIT;
            type  empty;
            description "To set the locator-led on or off.";
        } // END of locator-led-enable definition.

        leaf ddm-monitor-time-interval  {
            if-feature feature-list:NOT_HAVE_TIBIT;
            type  uint16 {
                 range "60..3600"  {
                    description "60..3600:60-3600 seconds";
                 }
            }
            description "To set DDM Monitor interval time.";
        } // END of ddm-monitor-time-interval definition.

        leaf vpiu-control-vlan  {
            if-feature feature-list:HAVE_VPIU_EMULATION;
            type  uint16 {
                 range "2..4094"  {
                    description "2..4094:VLAN ID 2 4094";
                 }
            }
            description "To set Video PIU Command VLAN.";
        } // END of vpiu-control-vlan definition.

        leaf service-unsupported-transceiver  {
            if-feature feature-list:NOT_HAVE_TIBIT;
            type  empty;
            description "To enable DDM Monitor for unsupported transceivers at user risk.";
        } // END of service-unsupported-transceiver definition.

        leaf enable-ddm-monitor  {
            if-feature feature-list:NOT_HAVE_TIBIT;
            type  empty;
            description "To enable DDM monitor for all transceivers.";
        } // END of enable-ddm-monitor definition.

        leaf disk-activity-monitoring-interval  {
            type  uint16 {
                 range "30..1200"  {
                    description "30..1200:30-1200 seconds";
                 }
            }
            description "To set disk activity sampling window interval time.";
        } // END of disk-activity-monitoring-interval definition.

        leaf disk-activity-monitoring-threshold-read  {
            type  uint32 {
                 range "1..20000"  {
                    description "1..20000:1-20000 KB/s";
                 }
            }
            description "To set disk read activity alarm threshold.";
        } // END of disk-activity-monitoring-threshold-read definition.

        leaf disk-activity-monitoring-threshold-write  {
            type  uint32 {
                 range "1..20000"  {
                    description "1..20000:1-20000 KB/s";
                 }
            }
            description "To set disk write activity alarm threshold.";
        } // END of disk-activity-monitoring-threshold-write definition.

    } // END of component-hardware-global definition.
    grouping gps-position-config {
        description
            "Grouping for gps position";
        choice gps-position-option {
            description
                "Use this attribute to choose between position option";
            case gps-position-disable {

                description
                    "Use this attribute to choose position disable.";

                leaf gps-position-disable  {
                    type  empty;
                    description "gps postion disable";
                } // END of gps-position-disable definition.

            }
            case gps-survey-in-observation-time {

                description
                    "Use this attribute to choose survey-in.";

                leaf gps-survey-in-observation-time  {
                    when " ../gps-survey-in-position-accuracy ";
                    type  uint32 {
                         range "1..1440"  {
                            description "1..1440:Minimum duration for survey-in in minutes";
                         }
                    }
                    description "GPS observation time";
                } // END of gps-survey-in-observation-time definition.

                leaf gps-survey-in-position-accuracy  {
                    when " ../gps-survey-in-observation-time ";
                    type  uint32 {
                         range "1..10000"  {
                            description "1..10000:Survey-in position accuracy limit in centimeters";
                         }
                    }
                    description "GPS position accuracy";
                } // END of gps-survey-in-position-accuracy definition.

            }
            case gps-fixed-latitude {

                description
                    "Use this attribute to choose fixed mode.";

                leaf gps-fixed-latitude  {
                    when " ../gps-fixed-longitude + ../gps-fixed-altitude ";
                    type  decimal64 {
                         fraction-digits 6;                    }
                    description "gps fixed latitude in decimal degree format";
                } // END of gps-fixed-latitude definition.

                leaf gps-fixed-longitude  {
                    when " ../gps-fixed-latitude + ../gps-fixed-altitude ";
                    type  decimal64 {
                         fraction-digits 6;                    }
                    description "GPS fixed longitude in decimal degree format";
                } // END of gps-fixed-longitude definition.

                leaf gps-fixed-altitude  {
                    when " ../gps-fixed-latitude + ../gps-fixed-longitude ";
                    type  decimal64 {
                         fraction-digits 6;                    }
                    description "GPS fixed altitude in meters";
                } // END of gps-fixed-altitude definition.

            }
        } // END of gps-position-option-choice definition.
    } // END of gps-position-config definition.
    grouping platform-sensor-record {
        description
            "Grouping sensor states";
        container bmc-sensor-data-record {
            if-feature feature-list:NOT_HAVE_TIBIT;
            config false;
            description
                "container enclosing bmc sensor data";
            uses component-bmc-sensor-record-state;
        } // END of bmc-sensor-data-record-container definition.
    } // END of platform-sensor-record definition.
    grouping platform-component-interface {
        description
            "Global interface configuration group";
        container interfaces {
            if-feature feature-list:NOT_HAVE_TIBIT;
            description
                "platform interface properties";
            uses platform-component-interface-list;
        } // END of interfaces-container definition.
    } // END of platform-component-interface definition.
    grouping gps-position-top {
        description
            "gps position configuration parameters";
        container gps-position {
            if-feature feature-list:HAVE_PTP_HW_OFFLOAD;
            description
                "container enclosing gps position parameters";
            container config {
                description
                    "configuration data for gps position";
                uses gps-position-config;
            } // END of config-container definition.
            container state {
                config false;
                description
                    "Global operational data";
                uses gps-position-config;
                uses temperature-grouping;
            } // END of state-container definition.
        } // END of gps-position-container definition.
    } // END of gps-position-top definition.
    grouping platform-component-global {
        description
            "Global configuration group for the platform";
        container global {
            description
                "container enclosing global configuration";
            container config {
                description
                    "configuration data for platform  global configuration";
                uses component-generic-global;
                uses component-hardware-global;
            } // END of config-container definition.
            container state {
                config false;
                description
                    "Global operational data";
                uses component-generic-global;
                uses component-hardware-global;
                uses temperature-grouping;
            } // END of state-container definition.
            uses system-load-cpu-usage-global;
            uses gps-position-top;
        } // END of global-container definition.
    } // END of platform-component-global definition.
    grouping platform-subcomponent-state {
        description
            "platformCMLSEPsubcomponentCMLSEPstate";
        leaf subcomponent-name  {
            type  leafref {
                path  "/components/component/state/name";
            }
            description "Reference to the name of the subcomponent";
        } // END of subcomponent-name definition.

    } // END of platform-subcomponent-state definition.
    grouping platform-subcomponent-top {
        description
            "platformCMLSEPsubcomponentCMLSEPtop";
        container subcomponents {
            config false;
            description
                "Enclosing container for subcomponent references";

            list subcomponent {
                key "subcomponent-name";
                config false;
                description
                    "List of subcomponent references";
                leaf subcomponent-name  {
                    type  leafref {
                        path  "../state/subcomponent-name";
                    }
                    description "References the component name";
                } // END of subcomponent-name definition.

                container state {
                    config false;
                    description
                        "Operational state data for the subcomponent";
                    uses platform-subcomponent-state;
                    uses temperature-grouping;
                } // END of state-container definition.
            } // End of subcomponent-list
        } // END of subcomponents-container definition.
    } // END of platform-subcomponent-top definition.
    grouping platform-component-debug {
        description
            "Global debug configuration group";
        container debug {
            description
                "configuration data for debug configuration";
            container config {
                description
                    "configuration data for cmm debug configuration";
                uses component-generic-debug;
                uses component-hardware-debug;
            } // END of config-container definition.
            container state {
                config false;
                description
                    "Operational data for debug";
                uses component-generic-debug;
                uses component-hardware-debug;
                uses component-generic-terminal-debug;
                uses component-hardware-terminal-debug;
                uses temperature-grouping;
            } // END of state-container definition.
        } // END of debug-container definition.
    } // END of platform-component-debug definition.

    grouping  components-grouping {
    description
        "Enclosing container for the components in the system.";
    container components {
        description
            "Enclosing container for the components in the system.";

        list component {
            key "name";
            config false;
            description
                "List of components, keyed by component name.";
            leaf name  {
                type  leafref {
                    path  "../state/name";
                }
                description "References the component name";
            } // END of name definition.

            container state {
                config false;
                description
                    "Operational state data for each component";
                leaf name  {
                    type  string {
                        length "1..1965";
                    }
                    description "References the component name";
                } // END of name definition.

                uses platform-component-state;
                uses platform-component-memory-state;
                uses platform-component-board-state;
                uses temperature-grouping;
            } // END of state-container definition.
            uses platform-sensor-record;
            uses platform-subcomponent-top;
            uses cpu-grouping;
            uses storage-grouping;
            uses ram-grouping;
            uses transceiver-grouping;
            uses power-supply-grouping;
            uses fan-grouping;
            uses fan-tray-grouping;
            uses chassis-grouping;
            uses linecard-grouping;
            uses power-rail-grouping;
            uses poe-grouping;
        } // End of component-list
        uses platform-component-debug;
        uses platform-component-global;
        uses platform-component-interface;
    } // END of components-container definition.
    } // END of components-grouping definition.

    uses components-grouping;
    uses profiles-grouping;
    uses hardware-grouping;

    rpc ddm-clear-transceiver-alarm-all {
        description "Use ddm-clear-transceiver-alarm-all to clear alarms from all
                    transceivers";
    }

    rpc ddm-clear-transceiver-alarm {
        description "Use ddm-clear-transceiver-alarm-all to clear alarm from transceiver";
        input  {
            leaf name  {
                type string;
                mandatory true;
                description "Use this rpc attribute to clear transceiver alarm";
            }
        }
    }

    rpc debug-ddm-on {
        description "Use debug-ddm-on to enable debug for digital diagnostic monitoring";
    }

    rpc debug-ddm-off {
        description "Use debug-ddm-off to disable debug for digital diagnostic monitoring";
    }

    rpc debug-cmm-on {
        description "Use debug-cmm-on to enable debug for chassis monitoring";
    }

    rpc debug-cmm-off {
        description "Use debug-cmm-off to disable debug for chassis monitoring";
    }

    notification bmc-lower-non-critical-low-threshold-notification {

        description "Notification for lower non critical low event.";

        // severity "WARNING";
        // eventClass "STATE";
        leaf name {
            type  string;
        description
            "References the component name";
        }

        leaf lower-non-critical {
            type  decimal64 {
                 fraction-digits 3;            }
        description
            "lower non critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-lower-non-critical-high-threshold-notification {

        description "Notification for lower non critical high event.";

        // severity "WARNING";
        // eventClass "STATE";
        leaf name {
            type  string;
        description
            "References the component name";
        }

        leaf lower-non-critical {
            type  decimal64 {
                 fraction-digits 3;            }
        description
            "lower non critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-lower-critical-low-threshold-notification {

        description "Notification for lower critical low event.";

        // severity "MAJOR";
        // eventClass "STATE";
        leaf name {
            type  string;
        description
            "References the component name";
        }

        leaf lower-critical {
            type  decimal64 {
                 fraction-digits 3;            }
        description
            "lower non critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-lower-critical-high-threshold-notification {

        description "Notification for lower critical high event.";

        // severity "WARNING";
        // eventClass "STATE";
        leaf name {
            type  string;
        description
            "References the component name";
        }

        leaf lower-critical {
            type  decimal64 {
                 fraction-digits 3;            }
        description
            "lower non critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-lower-non-recoverable-low-threshold-notification {

        description "Notification for lower non recoverable low event.";

        // severity "CRITICAL";
        // eventClass "STATE";
        leaf name {
            type  string;
        description
            "References the component name";
        }

        leaf lower-non-recoverable {
            type  decimal64 {
                 fraction-digits 3;            }
        description
            "lower non recoverable sensor threshold.-100002 represents not
                    applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-lower-non-recoverable-high-threshold-notification {

        description "Notification for lower non recoverable high event.";

        // severity "WARNING";
        // eventClass "STATE";
        leaf name {
            type  string;
        description
            "References the component name";
        }

        leaf lower-non-recoverable {
            type  decimal64 {
                 fraction-digits 3;            }
        description
            "lower non recoverable sensor threshold.-100002 represents not
                    applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-upper-non-critical-low-threshold-notification {

        description "Notification for upper non critical low event.";

        // severity "WARNING";
        // eventClass "STATE";
        leaf name {
            type  string;
        description
            "References the component name";
        }

        leaf upper-non-critical {
            type  decimal64 {
                 fraction-digits 3;            }
        description
            "upper non critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-upper-non-critical-high-threshold-notification {

        description "Notification for upper non critical high event.";

        // severity "WARNING";
        // eventClass "STATE";
        leaf name {
            type  string;
        description
            "References the component name";
        }

        leaf upper-non-critical {
            type  decimal64 {
                 fraction-digits 3;            }
        description
            "upper non critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-upper-critical-low-threshold-notification {

        description "Notification for upper critical low event.";

        // severity "WARNING";
        // eventClass "STATE";
        leaf name {
            type  string;
        description
            "References the component name";
        }

        leaf upper-critical {
            type  decimal64 {
                 fraction-digits 3;            }
        description
            "upper critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-upper-critical-high-threshold-notification {

        description "Notification for upper critical high event.";

        // severity "MAJOR";
        // eventClass "STATE";
        leaf name {
            type  string;
        description
            "References the component name";
        }

        leaf upper-critical {
            type  decimal64 {
                 fraction-digits 3;            }
        description
            "upper critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-upper-non-recoverable-low-threshold-notification {

        description "Notification for upper non recoverable low event.";

        // severity "WARNING";
        // eventClass "STATE";
        leaf name {
            type  string;
        description
            "References the component name";
        }

        leaf upper-non-recoverable {
            type  decimal64 {
                 fraction-digits 3;            }
        description
            "upper critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-upper-non-recoverable-high-threshold-notification {

        description "Notification for upper non recoverable high threshold high event.";

        // severity "CRITICAL";
        // eventClass "STATE";
        leaf name {
            type  string;
        description
            "References the component name";
        }

        leaf upper-non-recoverable {
            type  decimal64 {
                 fraction-digits 3;            }
        description
            "upper critical sensor threshold.-100002 represents not applicable";
        }

        leaf threshold {
            type  decimal64 {
                 fraction-digits 3;            }
        description
            "threshold for sensor notification";
        }

        leaf units {
            type  string;
        description
            "unit of sensor record";
        }

        leaf event-type {
            type ipi-platform-types:cmm_bmc_event_type_t;
        description
            "Type of event for sensor notification";
        }
    }

    notification bmc-device-state-notification {

        description "Notification for operational state of the device.";

        // severity "WARNING";
        // eventClass "STATE";
        leaf name {
            type  string;
        description
            "References the component name";
        }

        leaf operational-status {
            type  string;
        description
            "Sensor's operational state";
        }
    }

    notification cpu-load-15min-alert {

        description "This notification is sent when CPU utilization average during 15 minutes exceeds the alert threshold.";

        // severity "MAJOR";
        // eventClass "STATE";
        leaf name {
            type  string;
        description
            "References the component name";
        }

        leaf cpu-15min-load-percentage {
            type  decimal64 {
                 fraction-digits 2;            }
        description
            "The arithmetic mean value of the percentage measure of the CPU load
                    over 15 minutes interval";
        }

        leaf cpu-15min-alert-threshold {
            type  uint8;
        description
            "CPU load threshold during 15 minutes interval for alert level";
        }
    }

    notification cpu-load-15min-alert-recovery {

        description "This notification is sent when CPU utilization average during 15 minutes falls bellow the alert threshold.";

        // severity "INFO";
        // eventClass "STATE";
        leaf name {
            type  string;
        description
            "References the component name";
        }

        leaf cpu-15min-load-percentage {
            type  decimal64 {
                 fraction-digits 2;            }
        description
            "The arithmetic mean value of the percentage measure of the CPU load
                    over 15 minutes interval";
        }

        leaf cpu-15min-alert-threshold {
            type  uint8;
        description
            "CPU load threshold during 15 minutes interval for alert level";
        }
    }

    notification cpu-load-5min-alert {

        description "This notification is sent when CPU utilization average during 5 minutes exceeds the alert threshold.";

        // severity "MAJOR";
        // eventClass "STATE";
        leaf name {
            type  string;
        description
            "References the component name";
        }

        leaf cpu-5min-load-percentage {
            type  decimal64 {
                 fraction-digits 2;            }
        description
            "The arithmetic mean value of the percentage measure of the CPU load
                    over 5 minutes interval";
        }

        leaf cpu-5min-alert-threshold {
            type  uint8;
        description
            "CPU load threshold during 5 minutes interval for alert level";
        }
    }

    notification cpu-load-5min-alert-recovery {

        description "This notification is sent when CPU utilization average during 5 minutes falls bellow the alert threshold.";

        // severity "INFO";
        // eventClass "STATE";
        leaf name {
            type  string;
        description
            "References the component name";
        }

        leaf cpu-5min-load-percentage {
            type  decimal64 {
                 fraction-digits 2;            }
        description
            "The arithmetic mean value of the percentage measure of the CPU load
                    over 5 minutes interval";
        }

        leaf cpu-5min-alert-threshold {
            type  uint8;
        description
            "CPU load threshold during 5 minutes interval for alert level";
        }
    }

    notification cpu-load-1min-critical {

        description "This notification is sent when CPU utilization average during 1 minute exceeds the critical threshold.";

        // severity "CRITICAL";
        // eventClass "STATE";
        leaf name {
            type  string;
        description
            "References the component name";
        }

        leaf cpu-1min-load-percentage {
            type  decimal64 {
                 fraction-digits 2;            }
        description
            "The arithmetic mean value of the percentage measure of the CPU load
                    over 1 minute interval";
        }

        leaf cpu-1min-critical-threshold {
            type  uint8;
        description
            "CPU load threshold during 1 minute interval for critical level";
        }
    }

    notification cpu-load-1min-critical-recovery {

        description "This notification is sent when CPU utilization average during 1 minute falls bellow the critical threshold.";

        // severity "INFO";
        // eventClass "STATE";
        leaf name {
            type  string;
        description
            "References the component name";
        }

        leaf cpu-1min-load-percentage {
            type  decimal64 {
                 fraction-digits 2;            }
        description
            "The arithmetic mean value of the percentage measure of the CPU load
                    over 1 minute interval";
        }

        leaf cpu-1min-critical-threshold {
            type  uint8;
        description
            "CPU load threshold during 1 minute interval for critical level";
        }
    }

    notification cpu-load-1min-alert {

        description "This notification is sent when CPU utilization average during 1 minute falls bellow the alert threshold.";

        // severity "MAJOR";
        // eventClass "STATE";
        leaf name {
            type  string;
        description
            "References the component name";
        }

        leaf cpu-1min-load-percentage {
            type  decimal64 {
                 fraction-digits 2;            }
        description
            "The arithmetic mean value of the percentage measure of the CPU load
                    over 1 minute interval";
        }

        leaf cpu-1min-alert-threshold {
            type  uint8;
        description
            "CPU load threshold during 1 minute interval for alert level";
        }
    }

    notification cpu-load-1min-alert-recovery {

        description "This notification is sent when CPU utilization average during 1 minute falls bellow the alert threshold.";

        // severity "INFO";
        // eventClass "STATE";
        leaf name {
            type  string;
        description
            "References the component name";
        }

        leaf cpu-1min-load-percentage {
            type  decimal64 {
                 fraction-digits 2;            }
        description
            "The arithmetic mean value of the percentage measure of the CPU load
                    over 1 minute interval";
        }

        leaf cpu-1min-alert-threshold {
            type  uint8;
        description
            "CPU load threshold during 1 minute interval for alert level";
        }
    }

    notification storage-usage-rising-alert {

        description "Notification for storage when it exceeds alert threshold.";

        // severity "CRITICAL";
        // eventClass "STATE";
        leaf name {
            type  string;
        description
            "References the component name";
        }

        leaf used-memory {
            type  uint64;
        description
            "Used memory of the Hard storage.";
        }

        leaf usage-alert-threshold {
            type  int32;
        description
            "Hard disk's usage threshold %  for Alert Level.";
        }

        leaf mount-point {
            type  string;
        description
            "A unique value for each mounted filesystem.";
        }
    }

    notification storage-usage-critical-alert {

        description "Notification for storage when it exceeds critical threshold.";

        // severity "MAJOR";
        // eventClass "STATE";
        leaf name {
            type  string;
        description
            "References the component name";
        }

        leaf used-memory {
            type  uint64;
        description
            "Used memory of the Hard storage.";
        }

        leaf usage-critical-threshold {
            type  int32;
        description
            "Hard disk's usage threshold %  for critical level.";
        }

        leaf mount-point {
            type  string;
        description
            "A unique value for each mounted filesystem.";
        }
    }

    notification storage-usage-recovery-from-alert-level {

        description "Notification for storage usage recovery from alert level.";

        // severity "WARNING";
        // eventClass "STATE";
        leaf name {
            type  string;
        description
            "References the component name";
        }

        leaf used-memory {
            type  uint64;
        description
            "Used memory of the Hard storage.";
        }

        leaf usage-alert-threshold {
            type  int32;
        description
            "Hard disk's usage threshold %  for Alert Level.";
        }

        leaf mount-point {
            type  string;
        description
            "A unique value for each mounted filesystem.";
        }
    }

    notification storage-usage-recovery-from-critical-level {

        description "Notification for storage usage recovery from critical level.";

        // severity "WARNING";
        // eventClass "STATE";
        leaf name {
            type  string;
        description
            "References the component name";
        }

        leaf used-memory {
            type  uint64;
        description
            "Used memory of the Hard storage.";
        }

        leaf usage-critical-threshold {
            type  int32;
        description
            "Hard disk's usage threshold %  for critical level.";
        }

        leaf mount-point {
            type  string;
        description
            "A unique value for each mounted filesystem.";
        }
    }

    notification storage-remaining-life-rising-alert {

        description "Notification for storage disk remaining life when it exceeds alert threshold.";

        // severity "CRITICAL";
        // eventClass "STATE";
        leaf name {
            type  string;
        description
            "References the component name";
        }

        leaf remaining-life {
            type  int32;
        description
            "Hard disk's Remain life % Values.";
        }

        leaf remain-life-alert-threshold {
            type  int32;
        description
            "Hard disk's Remain Life threshold % for Alert Level.";
        }
    }

    notification storage-remaining-life-rising-critical {

        description "Notification for storage disk remaining life when it exceeds critical threshold.";

        // severity "MAJOR";
        // eventClass "STATE";
        leaf name {
            type  string;
        description
            "References the component name";
        }

        leaf remaining-life {
            type  int32;
        description
            "Hard disk's Remain life % Values.";
        }

        leaf remain-life-critical-threshold {
            type  int32;
        description
            "Hard disk's Remain Life threshold % for Critical Level.";
        }
    }

    notification storage-available-reserved-space-rising-alert {

        description "Notification for storage available reserved space when it exceeds alert threshold.";

        // severity "CRITICAL";
        // eventClass "STATE";
        leaf name {
            type  string;
        description
            "References the component name";
        }

        leaf available-reserved-space {
            type  int32;
        description
            "Hard disk's Available Reserved Space % values";
        }

        leaf available-reserved-space-alert-threshold {
            type  int32;
        description
            "Hard disk's Available Reserved Space threshold % values for Alert
                    Level.";
        }
    }

    notification storage-available-reserved-space-rising-critical {

        description "Notification for storage available reserved space when it exceeds critical threshold.";

        // severity "MAJOR";
        // eventClass "STATE";
        leaf name {
            type  string;
        description
            "References the component name";
        }

        leaf available-reserved-space {
            type  int32;
        description
            "Hard disk's Available Reserved Space % values";
        }

        leaf available-reserved-space-critical-threshold {
            type  int32;
        description
            "Hard disk's Available Reserved Space threshold % values for critical
                    Level.";
        }
    }

    notification storage-reallocated-sector-count-rising-alert {

        description "Notification for storage reallocated-sector-count when it increments by 10.";

        // severity "CRITICAL";
        // eventClass "STATE";
        leaf name {
            type  string;
        description
            "References the component name";
        }

        leaf reallocated-sector-count {
            type  int32;
        description
            "Hard disk's Reallocated Sectors Count values.";
        }
    }

    notification storage-uncorrectable-sector-count-rising-critical {

        description "Notification for storage uncorrectable-sector-count when it count increments by 1..";

        // severity "MAJOR";
        // eventClass "STATE";
        leaf name {
            type  string;
        description
            "References the component name";
        }

        leaf uncorrectable-sector-count {
            type  int32;
        description
            "Hard disk's Uncorrectable Sectors Count.";
        }
    }

    notification storage-harddisk-monitoring-read-alert {

        description "Notification for storage harddisk read activity when it exceeds alert threshold.";

        // severity "CRITICAL";
        // eventClass "STATE";
        leaf name {
            type  string;
        description
            "References the component name";
        }

        leaf harddisk-monitoring-read {
            type  int32;
        description
            "Hard disk's average read activity in KBps.";
        }

        leaf harddisk-monitoring-read-threshold {
            type  int32;
        description
            "Hard disk's read activity threshold in KBps.";
        }
    }

    notification storage-harddisk-recovery-from-read-alert-level {

        description "Notification for storage harddisk read activity when it recovers from alert level.";

        // severity "INFO";
        // eventClass "STATE";
        leaf name {
            type  string;
        description
            "References the component name";
        }

        leaf harddisk-monitoring-read {
            type  int32;
        description
            "Hard disk's average read activity in KBps.";
        }

        leaf harddisk-monitoring-read-threshold {
            type  int32;
        description
            "Hard disk's read activity threshold in KBps.";
        }
    }

    notification storage-harddisk-monitoring-write-alert {

        description "Notification for storage harddisk write activity when it exceeds alert threshold.";

        // severity "CRITICAL";
        // eventClass "STATE";
        leaf name {
            type  string;
        description
            "References the component name";
        }

        leaf harddisk-monitoring-write {
            type  int32;
        description
            "Hard disk's average write activity in KBps.";
        }

        leaf harddisk-monitoring-write-threshold {
            type  int32;
        description
            "Hard disk's write activity threshold in KBps.";
        }
    }

    notification storage-harddisk-recovery-from-write-alert-level {

        description "Notification for storage harddisk write activity when it recovers from alert level.";

        // severity "INFO";
        // eventClass "STATE";
        leaf name {
            type  string;
        description
            "References the component name";
        }

        leaf harddisk-monitoring-write {
            type  int32;
        description
            "Hard disk's average write activity in KBps.";
        }

        leaf harddisk-monitoring-write-threshold {
            type  int32;
        description
            "Hard disk's write activity threshold in KBps.";
        }
    }

    notification storage-storage-status-alert {

        description "Notification for storage disk eol status is in alert level.";

        // severity "CRITICAL";
        // eventClass "STATE";
        leaf name {
            type  string;
        description
            "References the component name";
        }

        leaf storage-status {
            type ipi-platform-types:cml_cmm_storage_status_t;
        description
            "Hard disk's eol status.";
        }
    }

    notification storage-storage-status-critical {

        description "Notification for storage disk eol status is in critical level.";

        // severity "MAJOR";
        // eventClass "STATE";
        leaf name {
            type  string;
        description
            "References the component name";
        }

        leaf storage-status {
            type ipi-platform-types:cml_cmm_storage_status_t;
        description
            "Hard disk's eol status.";
        }
    }

    notification ram-usage-rising-critical {

        description "Notification for RAM usage rising critical threshold.";

        // severity "CRITICAL";
        // eventClass "STATE";
        leaf name {
            type  string;
        description
            "References the component name";
        }

        leaf used-memory {
            type  uint64;
        description
            "CPU RAM's used memory available for utilisation in MBytes.";
        }

        leaf usage-critical-threshold {
            type  uint32;
        description
            "RAM usage threshold % for critical level.";
        }
    }

    notification ram-usage-rising-alert {

        description "Notification for RAM usage rising alert threshold.";

        // severity "CRITICAL";
        // eventClass "STATE";
        leaf name {
            type  string;
        description
            "References the component name";
        }

        leaf used-memory {
            type  uint64;
        description
            "CPU RAM's used memory available for utilisation in MBytes.";
        }

        leaf usage-alert-threshold {
            type  uint32;
        description
            "RAM usage threshold % for alert level.";
        }
    }

    notification ram-usage-recovery-from-critical-level {

        description "Notification for RAM usage recovery from critical threshold.";

        // severity "WARNING";
        // eventClass "STATE";
        leaf name {
            type  string;
        description
            "References the component name";
        }

        leaf used-memory {
            type  uint64;
        description
            "CPU RAM's used memory available for utilisation in MBytes.";
        }

        leaf usage-critical-threshold {
            type  uint32;
        description
            "RAM usage threshold % for critical level.";
        }
    }

    notification ram-usage-recovery-from-alert-level {

        description "Notification for RAM usage recovery from alert threshold.";

        // severity "WARNING";
        // eventClass "STATE";
        leaf name {
            type  string;
        description
            "References the component name";
        }

        leaf used-memory {
            type  uint64;
        description
            "CPU RAM's used memory available for utilisation in MBytes.";
        }

        leaf usage-alert-threshold {
            type  uint32;
        description
            "RAM usage threshold % for alert level.";
        }
    }

    notification transceiver-inserted {

        description "Notification triggered when a transceiver is inserted..";

        // severity "WARNING";
        // eventClass "STATE";
        leaf name {
            type  string;
        description
            "References the component name";
        }

        leaf port-no {
            type  uint8;
        description
            "Transceiver port number";
        }

        leaf type {
            type ipi-platform-transceiver-types:ddm_cmm_trans_type_t;
        description
            "Type of the transceiver SFP/QSFP.";
        }

        leaf vendor-name {
            type  string;
        description
            "Transceiver vendor name.";
        }

        leaf vendor-serial-number {
            type  string;
        description
            "Serial number provided by vendor.";
        }

        leaf connector-type {
            type ipi-platform-transceiver-types:ddm_cmm_trans_connector_type_t;
        description
            "Connector type for the transceiver.";
        }
    }

    notification transceiver-removed {

        description "Notification triggered when a transceiver is removed..";

        // severity "WARNING";
        // eventClass "STATE";
        leaf name {
            type  string;
        description
            "References the component name";
        }

        leaf port-no {
            type  uint8;
        description
            "Transceiver port number";
        }

        leaf type {
            type ipi-platform-transceiver-types:ddm_cmm_trans_type_t;
        description
            "Type of the transceiver SFP/QSFP.";
        }

        leaf vendor-name {
            type  string;
        description
            "Transceiver vendor name.";
        }

        leaf vendor-serial-number {
            type  string;
        description
            "Serial number provided by vendor.";
        }

        leaf connector-type {
            type ipi-platform-transceiver-types:ddm_cmm_trans_connector_type_t;
        description
            "Connector type for the transceiver.";
        }
    }

    notification faulty-transceiver-inserted {

        description "Notification triggered when a faulty transceiver is inserted..";

        // severity "WARNING";
        // eventClass "STATE";
        leaf name {
            type  string;
        description
            "References the component name";
        }

        leaf port-no {
            type  uint8;
        description
            "Transceiver port number";
        }

        leaf type {
            type ipi-platform-transceiver-types:ddm_cmm_trans_type_t;
        description
            "Type of the transceiver SFP/QSFP.";
        }
    }

    notification incompatible-transceiver-inserted {

        description "Notification triggered when an incompatible transceiver is inserted..";

        // severity "CRITICAL";
        // eventClass "STATE";
        leaf name {
            type  string;
        description
            "References the component name";
        }

        leaf port-no {
            type  uint8;
        description
            "Transceiver port number";
        }
    }

    notification incompatible-transceiver-removed {

        description "Notification triggered when an incompatible transceiver is removed..";

        // severity "INFO";
        // eventClass "STATE";
        leaf name {
            type  string;
        description
            "References the component name";
        }

        leaf port-no {
            type  uint8;
        description
            "Transceiver port number";
        }
    }

    notification frequency-error-high-critical {

        description "This notification is sent when frequency-error register exceeds the high-critical threshold.";

        // severity "MAJOR";
        // eventClass "STATE";
        leaf name {
            type  string;
        description
            "References the component name";
        }

        leaf frequency-error {
            type  decimal64 {
                 fraction-digits 2;            }
        description
            "Transceiver frequency error";
        }

        leaf frequency-error-critical-min-threshold {
            type  decimal64 {
                 fraction-digits 2;            }
        description
            "The minimum critical threshold for transceiver frequency-error";
        }

        leaf frequency-error-critical-max-threshold {
            type  decimal64 {
                 fraction-digits 2;            }
        description
            "The maximum critical threshold for transceiver frequency-error";
        }
    }

    notification frequency-error-low-critical {

        description "This notification is sent when frequency-error register exceeds the low-critical threshold.";

        // severity "MAJOR";
        // eventClass "STATE";
        leaf name {
            type  string;
        description
            "References the component name";
        }

        leaf frequency-error {
            type  decimal64 {
                 fraction-digits 2;            }
        description
            "Transceiver frequency error";
        }

        leaf frequency-error-critical-min-threshold {
            type  decimal64 {
                 fraction-digits 2;            }
        description
            "The minimum critical threshold for transceiver frequency-error";
        }

        leaf frequency-error-critical-max-threshold {
            type  decimal64 {
                 fraction-digits 2;            }
        description
            "The maximum critical threshold for transceiver frequency-error";
        }
    }

    notification frequency-error-high-alert {

        description "This notification is sent when frequency-error register exceeds the high-alert threshold.";

        // severity "CRITICAL";
        // eventClass "STATE";
        leaf name {
            type  string;
        description
            "References the component name";
        }

        leaf frequency-error {
            type  decimal64 {
                 fraction-digits 2;            }
        description
            "Transceiver frequency error";
        }

        leaf frequency-error-alert-min-threshold {
            type  decimal64 {
                 fraction-digits 2;            }
        description
            "The minimum alert threshold for transceiver frequency-error";
        }

        leaf frequency-error-alert-max-threshold {
            type  decimal64 {
                 fraction-digits 2;            }
        description
            "The maximum alert threshold for transceiver frequency-error";
        }
    }

    notification frequency-error-low-alert {

        description "This notification is sent when frequency-error register exceeds the low-alert threshold.";

        // severity "CRITICAL";
        // eventClass "STATE";
        leaf name {
            type  string;
        description
            "References the component name";
        }

        leaf frequency-error {
            type  decimal64 {
                 fraction-digits 2;            }
        description
            "Transceiver frequency error";
        }

        leaf frequency-error-alert-min-threshold {
            type  decimal64 {
                 fraction-digits 2;            }
        description
            "The minimum alert threshold for transceiver frequency-error";
        }

        leaf frequency-error-alert-max-threshold {
            type  decimal64 {
                 fraction-digits 2;            }
        description
            "The maximum alert threshold for transceiver frequency-error";
        }
    }

    notification frequency-error-recovery {

        description "This notification is sent when frequency-error register exceeds threshold.";

        // severity "WARNING";
        // eventClass "STATE";
        leaf name {
            type  string;
        description
            "References the component name";
        }

        leaf frequency-error {
            type  decimal64 {
                 fraction-digits 2;            }
        description
            "Transceiver frequency error";
        }
    }

    notification wavelength-error-high-critical {

        description "This notification is sent when wavelength-error register exceeds the high-critical threshold.";

        // severity "MAJOR";
        // eventClass "STATE";
        leaf name {
            type  string;
        description
            "References the component name";
        }

        leaf wavelength-error {
            type  decimal64 {
                 fraction-digits 4;            }
        description
            "Transceiver wavelength error";
        }

        leaf wavelength-error-critical-min-threshold {
            type  decimal64 {
                 fraction-digits 4;            }
        description
            "The minimum critical threshold for transceiver wavelength-error";
        }

        leaf wavelength-error-critical-max-threshold {
            type  decimal64 {
                 fraction-digits 4;            }
        description
            "The maximum critical threshold for transceiver wavelength-error";
        }
    }

    notification wavelength-error-low-critical {

        description "This notification is sent when wavelength-error register exceeds the low-critical threshold.";

        // severity "MAJOR";
        // eventClass "STATE";
        leaf name {
            type  string;
        description
            "References the component name";
        }

        leaf wavelength-error {
            type  decimal64 {
                 fraction-digits 4;            }
        description
            "Transceiver wavelength error";
        }

        leaf wavelength-error-critical-min-threshold {
            type  decimal64 {
                 fraction-digits 4;            }
        description
            "The minimum critical threshold for transceiver wavelength-error";
        }

        leaf wavelength-error-critical-max-threshold {
            type  decimal64 {
                 fraction-digits 4;            }
        description
            "The maximum critical threshold for transceiver wavelength-error";
        }
    }

    notification wavelength-error-high-alert {

        description "This notification is sent when wavelength-error register exceeds the high-alert threshold.";

        // severity "CRITICAL";
        // eventClass "STATE";
        leaf name {
            type  string;
        description
            "References the component name";
        }

        leaf wavelength-error {
            type  decimal64 {
                 fraction-digits 4;            }
        description
            "Transceiver wavelength error";
        }

        leaf wavelength-error-alert-min-threshold {
            type  decimal64 {
                 fraction-digits 4;            }
        description
            "The minimum alert threshold for transceiver wavelength-error";
        }

        leaf wavelength-error-alert-max-threshold {
            type  decimal64 {
                 fraction-digits 4;            }
        description
            "The maximum alert threshold for transceiver wavelength-error";
        }
    }

    notification wavelength-error-low-alert {

        description "This notification is sent when wavelength-error register exceeds the low-alert threshold.";

        // severity "CRITICAL";
        // eventClass "STATE";
        leaf name {
            type  string;
        description
            "References the component name";
        }

        leaf wavelength-error {
            type  decimal64 {
                 fraction-digits 4;            }
        description
            "Transceiver wavelength error";
        }

        leaf wavelength-error-alert-min-threshold {
            type  decimal64 {
                 fraction-digits 4;            }
        description
            "The minimum alert threshold for transceiver wavelength-error";
        }

        leaf wavelength-error-alert-max-threshold {
            type  decimal64 {
                 fraction-digits 4;            }
        description
            "The maximum alert threshold for transceiver wavelength-error";
        }
    }

    notification wavelength-error-recovery {

        description "This notification is sent when wavelength-error register exceeds threshold.";

        // severity "WARNING";
        // eventClass "STATE";
        leaf name {
            type  string;
        description
            "References the component name";
        }

        leaf wavelength-error {
            type  decimal64 {
                 fraction-digits 4;            }
        description
            "Transceiver wavelength error";
        }
    }

    notification thermoelectric-cooler-fault-alert {

        description "This notification is sent when transceiver is on error thermoelectric-cooler-fault.";

        // severity "CRITICAL";
        // eventClass "STATE";
        leaf name {
            type  string;
        description
            "References the component name";
        }

        leaf thermoelectric-cooler-fault {
            type  boolean;
        description
            "Thermo-electric cooler fault indication";
        }
    }

    notification thermoelectric-cooler-fault-recovery {

        description "This notification is sent when transceiver is recovered from error thermoelectric-cooler-fault.";

        // severity "WARNING";
        // eventClass "STATE";
        leaf name {
            type  string;
        description
            "References the component name";
        }

        leaf thermoelectric-cooler-fault {
            type  boolean;
        description
            "Thermo-electric cooler fault indication";
        }
    }

    notification rx-loss-of-signal {

        description "This notification is sent when rx_loss is detected on qspf/sfp/xfp port.";

        // severity "CRITICAL";
        // eventClass "STATE";
        leaf index {
            type  uint8;
        description
            "A unique value, greater than zero, for each channel in the transceiver
                    within the unit.";
        }

        leaf name {
            type  string;
        description
            "References the component name";
        }
    }

    notification rx-loss-of-signal-recovery {

        description "This notification is sent when rx_loss is recovery on qspf/sfp/xfp port.";

        // severity "INFO";
        // eventClass "STATE";
        leaf index {
            type  uint8;
        description
            "A unique value, greater than zero, for each channel in the transceiver
                    within the unit.";
        }

        leaf name {
            type  string;
        description
            "References the component name";
        }
    }

    notification temperature-high {

        description "This notification is sent when temperature sensor exceeds a given threshold.";

        // eventClass "STATE";
        leaf name {
            type  string;
        description
            "References the component name";
        }

        leaf alarm-status {
            type  boolean;
        description
            "A value of true indicates the alarm has been raised or asserted. The
                    value should be false when the alarm is cleared.";
        }

        leaf alarm-threshold {
            type  decimal64 {
                 fraction-digits 2;            }
        description
            "The threshold value that was crossed for this alarm.";
        }

        leaf instant {
            type  decimal64 {
                 fraction-digits 2;            }
        description
            "The instantaneous temperature value.";
        }
    }

    notification temperature-low {

        description "This notification is sent when temperature sensor falls below a given threshold.";

        // eventClass "STATE";
        leaf name {
            type  string;
        description
            "References the component name";
        }

        leaf alarm-status {
            type  boolean;
        description
            "A value of true indicates the alarm has been raised or asserted. The
                    value should be false when the alarm is cleared.";
        }

        leaf alarm-threshold {
            type  decimal64 {
                 fraction-digits 2;            }
        description
            "The threshold value that was crossed for this alarm.";
        }

        leaf instant {
            type  decimal64 {
                 fraction-digits 2;            }
        description
            "The instantaneous temperature value.";
        }
    }

    notification power-supply-inserted {

        description "This notification is sent when power supply unit is inserted.";

        // severity "WARNING";
        // eventClass "STATE";
        leaf name {
            type  string;
        description
            "References the component name";
        }
    }

    notification power-supply-removed {

        description "This notification is sent when power supply unit is removed.";

        // severity "WARNING";
        // eventClass "STATE";
        leaf name {
            type  string;
        description
            "References the component name";
        }
    }

    notification power-supply-ac-failed {

        description "This notification is sent when power supply unit has no input power.";

        // severity "CRITICAL";
        // eventClass "STATE";
        leaf name {
            type  string;
        description
            "References the component name";
        }
    }

    notification power-supply-ac-recovery {

        description "This notification is sent when power supply unit input power is restored.";

        // severity "INFO";
        // eventClass "STATE";
        leaf name {
            type  string;
        description
            "References the component name";
        }
    }

    notification power-supply-12v-failed {

        description "This notification is sent when power supply unit has no output power.";

        // severity "CRITICAL";
        // eventClass "STATE";
        leaf name {
            type  string;
        description
            "References the component name";
        }
    }

    notification power-supply-12v-recovery {

        description "This notification is sent when power supply unit output power is restored..";

        // severity "INFO";
        // eventClass "STATE";
        leaf name {
            type  string;
        description
            "References the component name";
        }
    }

    notification psu-vin-low-alert {

        description "This notification is sent when input voltage of PSU exceeds a given threshold.";

        // severity "CRITICAL";
        // eventClass "STATE";
        leaf name {
            type  string;
        description
            "References the component name";
        }

        leaf input-voltage {
            type  decimal64 {
                 fraction-digits 2;            }
        description
            "Input voltage of power supply";
        }

        leaf vin-alert-threshold-min {
            type  decimal64 {
                 fraction-digits 2;            }
        description
            "Psu input volatge alert threshold minimum value";
        }

        leaf vin-alert-threshold-max {
            type  decimal64 {
                 fraction-digits 2;            }
        description
            "Psu input volatge alert threshold maximum value";
        }
    }

    notification psu-vin-high-alert {

        description "This notification is sent when input voltage of PSU exceeds a given threshold.";

        // severity "CRITICAL";
        // eventClass "STATE";
        leaf name {
            type  string;
        description
            "References the component name";
        }

        leaf input-voltage {
            type  decimal64 {
                 fraction-digits 2;            }
        description
            "Input voltage of power supply";
        }

        leaf vin-alert-threshold-min {
            type  decimal64 {
                 fraction-digits 2;            }
        description
            "Psu input volatge alert threshold minimum value";
        }

        leaf vin-alert-threshold-max {
            type  decimal64 {
                 fraction-digits 2;            }
        description
            "Psu input volatge alert threshold maximum value";
        }
    }

    notification psu-vin-low-critical {

        description "This notification is sent when input voltage of PSU exceeds a given threshold.";

        // severity "CRITICAL";
        // eventClass "STATE";
        leaf name {
            type  string;
        description
            "References the component name";
        }

        leaf input-voltage {
            type  decimal64 {
                 fraction-digits 2;            }
        description
            "Input voltage of power supply";
        }

        leaf vin-critical-threshold-min {
            type  decimal64 {
                 fraction-digits 2;            }
        description
            "Psu input volatge critical threshold minimun value";
        }

        leaf vin-critical-threshold-max {
            type  decimal64 {
                 fraction-digits 2;            }
        description
            "Psu input volatge critical threshold maximum value";
        }
    }

    notification psu-vin-high-critical {

        description "This notification is sent when input voltage of PSU exceeds a given threshold.";

        // severity "CRITICAL";
        // eventClass "STATE";
        leaf name {
            type  string;
        description
            "References the component name";
        }

        leaf input-voltage {
            type  decimal64 {
                 fraction-digits 2;            }
        description
            "Input voltage of power supply";
        }

        leaf vin-critical-threshold-min {
            type  decimal64 {
                 fraction-digits 2;            }
        description
            "Psu input volatge critical threshold minimun value";
        }

        leaf vin-critical-threshold-max {
            type  decimal64 {
                 fraction-digits 2;            }
        description
            "Psu input volatge critical threshold maximum value";
        }
    }

    notification psu-vin-low-alert-recovery {

        description "This notification is sent when input voltage of PSU exceeds a given threshold.";

        // severity "INFO";
        // eventClass "STATE";
        leaf name {
            type  string;
        description
            "References the component name";
        }

        leaf input-voltage {
            type  decimal64 {
                 fraction-digits 2;            }
        description
            "Input voltage of power supply";
        }

        leaf vin-alert-threshold-min {
            type  decimal64 {
                 fraction-digits 2;            }
        description
            "Psu input volatge alert threshold minimum value";
        }

        leaf vin-alert-threshold-max {
            type  decimal64 {
                 fraction-digits 2;            }
        description
            "Psu input volatge alert threshold maximum value";
        }
    }

    notification psu-vin-high-alert-recovery {

        description "This notification is sent when input voltage of PSU exceeds a given threshold.";

        // severity "INFO";
        // eventClass "STATE";
        leaf name {
            type  string;
        description
            "References the component name";
        }

        leaf input-voltage {
            type  decimal64 {
                 fraction-digits 2;            }
        description
            "Input voltage of power supply";
        }

        leaf vin-alert-threshold-min {
            type  decimal64 {
                 fraction-digits 2;            }
        description
            "Psu input volatge alert threshold minimum value";
        }

        leaf vin-alert-threshold-max {
            type  decimal64 {
                 fraction-digits 2;            }
        description
            "Psu input volatge alert threshold maximum value";
        }
    }

    notification psu-vin-low-critical-recovery {

        description "This notification is sent when input voltage of PSU exceeds a given threshold.";

        // severity "INFO";
        // eventClass "STATE";
        leaf name {
            type  string;
        description
            "References the component name";
        }

        leaf input-voltage {
            type  decimal64 {
                 fraction-digits 2;            }
        description
            "Input voltage of power supply";
        }

        leaf vin-critical-threshold-min {
            type  decimal64 {
                 fraction-digits 2;            }
        description
            "Psu input volatge critical threshold minimun value";
        }

        leaf vin-critical-threshold-max {
            type  decimal64 {
                 fraction-digits 2;            }
        description
            "Psu input volatge critical threshold maximum value";
        }
    }

    notification psu-vin-high-critical-recovery {

        description "This notification is sent when input voltage of PSU exceeds a given threshold.";

        // severity "INFO";
        // eventClass "STATE";
        leaf name {
            type  string;
        description
            "References the component name";
        }

        leaf input-voltage {
            type  decimal64 {
                 fraction-digits 2;            }
        description
            "Input voltage of power supply";
        }

        leaf vin-critical-threshold-min {
            type  decimal64 {
                 fraction-digits 2;            }
        description
            "Psu input volatge critical threshold minimun value";
        }

        leaf vin-critical-threshold-max {
            type  decimal64 {
                 fraction-digits 2;            }
        description
            "Psu input volatge critical threshold maximum value";
        }
    }

    notification psu-vout-low-alert {

        description "This notification is sent when output voltage of PSU exceeds a given threshold.";

        // severity "CRITICAL";
        // eventClass "STATE";
        leaf name {
            type  string;
        description
            "References the component name";
        }

        leaf output-voltage {
            type  decimal64 {
                 fraction-digits 2;            }
        description
            "Output voltage of power supply";
        }

        leaf vout-alert-threshold-min {
            type  decimal64 {
                 fraction-digits 2;            }
        description
            "Psu output volatge alert threshold minimum value";
        }

        leaf vout-alert-threshold-max {
            type  decimal64 {
                 fraction-digits 2;            }
        description
            "Psu output volatge alert threshold maximum value";
        }
    }

    notification psu-vout-high-alert {

        description "This notification is sent when output voltage of PSU exceeds a given threshold.";

        // severity "CRITICAL";
        // eventClass "STATE";
        leaf name {
            type  string;
        description
            "References the component name";
        }

        leaf output-voltage {
            type  decimal64 {
                 fraction-digits 2;            }
        description
            "Output voltage of power supply";
        }

        leaf vout-alert-threshold-min {
            type  decimal64 {
                 fraction-digits 2;            }
        description
            "Psu output volatge alert threshold minimum value";
        }

        leaf vout-alert-threshold-max {
            type  decimal64 {
                 fraction-digits 2;            }
        description
            "Psu output volatge alert threshold maximum value";
        }
    }

    notification psu-vout-low-critical {

        description "This notification is sent when output voltage of PSU exceeds a given threshold.";

        // severity "CRITICAL";
        // eventClass "STATE";
        leaf name {
            type  string;
        description
            "References the component name";
        }

        leaf output-voltage {
            type  decimal64 {
                 fraction-digits 2;            }
        description
            "Output voltage of power supply";
        }

        leaf vout-critical-threshold-min {
            type  decimal64 {
                 fraction-digits 2;            }
        description
            "Psu output volatge critical threshold minimum value";
        }

        leaf vout-critical-threshold-max {
            type  decimal64 {
                 fraction-digits 2;            }
        description
            "Psu output volatge critical threshold maximum value";
        }
    }

    notification psu-vout-high-critical {

        description "This notification is sent when output voltage of PSU exceeds a given threshold.";

        // severity "CRITICAL";
        // eventClass "STATE";
        leaf name {
            type  string;
        description
            "References the component name";
        }

        leaf output-voltage {
            type  decimal64 {
                 fraction-digits 2;            }
        description
            "Output voltage of power supply";
        }

        leaf vout-critical-threshold-min {
            type  decimal64 {
                 fraction-digits 2;            }
        description
            "Psu output volatge critical threshold minimum value";
        }

        leaf vout-critical-threshold-max {
            type  decimal64 {
                 fraction-digits 2;            }
        description
            "Psu output volatge critical threshold maximum value";
        }
    }

    notification psu-vout-low-alert-recovery {

        description "This notification is sent when output voltage of PSU exceeds a given threshold.";

        // severity "INFO";
        // eventClass "STATE";
        leaf name {
            type  string;
        description
            "References the component name";
        }

        leaf output-voltage {
            type  decimal64 {
                 fraction-digits 2;            }
        description
            "Output voltage of power supply";
        }

        leaf vout-alert-threshold-min {
            type  decimal64 {
                 fraction-digits 2;            }
        description
            "Psu output volatge alert threshold minimum value";
        }

        leaf vout-alert-threshold-max {
            type  decimal64 {
                 fraction-digits 2;            }
        description
            "Psu output volatge alert threshold maximum value";
        }
    }

    notification psu-vout-high-alert-recovery {

        description "This notification is sent when output voltage violation is recovered.";

        // severity "INFO";
        // eventClass "STATE";
        leaf name {
            type  string;
        description
            "References the component name";
        }

        leaf output-voltage {
            type  decimal64 {
                 fraction-digits 2;            }
        description
            "Output voltage of power supply";
        }

        leaf vout-alert-threshold-min {
            type  decimal64 {
                 fraction-digits 2;            }
        description
            "Psu output volatge alert threshold minimum value";
        }

        leaf vout-alert-threshold-max {
            type  decimal64 {
                 fraction-digits 2;            }
        description
            "Psu output volatge alert threshold maximum value";
        }
    }

    notification psu-vout-low-critical-recovery {

        description "This notification is sent when output voltage violation is recovered.";

        // severity "INFO";
        // eventClass "STATE";
        leaf name {
            type  string;
        description
            "References the component name";
        }

        leaf output-voltage {
            type  decimal64 {
                 fraction-digits 2;            }
        description
            "Output voltage of power supply";
        }

        leaf vout-critical-threshold-min {
            type  decimal64 {
                 fraction-digits 2;            }
        description
            "Psu output volatge critical threshold minimum value";
        }

        leaf vout-critical-threshold-max {
            type  decimal64 {
                 fraction-digits 2;            }
        description
            "Psu output volatge critical threshold maximum value";
        }
    }

    notification psu-vout-high-critical-recovery {

        description "This notification is sent when output voltage violation is recovered.";

        // severity "INFO";
        // eventClass "STATE";
        leaf name {
            type  string;
        description
            "References the component name";
        }

        leaf output-voltage {
            type  decimal64 {
                 fraction-digits 2;            }
        description
            "Output voltage of power supply";
        }

        leaf vout-critical-threshold-min {
            type  decimal64 {
                 fraction-digits 2;            }
        description
            "Psu output volatge critical threshold minimum value";
        }

        leaf vout-critical-threshold-max {
            type  decimal64 {
                 fraction-digits 2;            }
        description
            "Psu output volatge critical threshold maximum value";
        }
    }

    notification psu-pin-low-alert {

        description "This notification is sent when input power of PSU exceeds a given threshold.";

        // severity "CRITICAL";
        // eventClass "STATE";
        leaf name {
            type  string;
        description
            "References the component name";
        }

        leaf input-power {
            type  decimal64 {
                 fraction-digits 2;            }
        description
            "Input power of power supply";
        }

        leaf pin-alert-threshold-min {
            type  decimal64 {
                 fraction-digits 2;            }
        description
            "Psu input power alert threshold minimum value";
        }

        leaf pin-alert-threshold-max {
            type  decimal64 {
                 fraction-digits 2;            }
        description
            "Psu input power alert threshold maximum value";
        }
    }

    notification psu-pin-high-alert {

        description "This notification is sent when input power of PSU exceeds a given threshold.";

        // severity "CRITICAL";
        // eventClass "STATE";
        leaf name {
            type  string;
        description
            "References the component name";
        }

        leaf input-power {
            type  decimal64 {
                 fraction-digits 2;            }
        description
            "Input power of power supply";
        }

        leaf pin-alert-threshold-min {
            type  decimal64 {
                 fraction-digits 2;            }
        description
            "Psu input power alert threshold minimum value";
        }

        leaf pin-alert-threshold-max {
            type  decimal64 {
                 fraction-digits 2;            }
        description
            "Psu input power alert threshold maximum value";
        }
    }

    notification psu-pin-low-critical {

        description "This notification is sent when input power of PSU exceeds a given threshold.";

        // severity "CRITICAL";
        // eventClass "STATE";
        leaf name {
            type  string;
        description
            "References the component name";
        }

        leaf input-power {
            type  decimal64 {
                 fraction-digits 2;            }
        description
            "Input power of power supply";
        }

        leaf pin-critical-threshold-min {
            type  decimal64 {
                 fraction-digits 2;            }
        description
            "Psu input power critical threshold minimum value";
        }

        leaf pin-critical-threshold-max {
            type  decimal64 {
                 fraction-digits 2;            }
        description
            "Psu input power critical threshold maximum value";
        }
    }

    notification psu-pin-high-critical {

        description "This notification is sent when input power of PSU exceeds a given threshold.";

        // severity "CRITICAL";
        // eventClass "STATE";
        leaf name {
            type  string;
        description
            "References the component name";
        }

        leaf input-power {
            type  decimal64 {
                 fraction-digits 2;            }
        description
            "Input power of power supply";
        }

        leaf pin-critical-threshold-min {
            type  decimal64 {
                 fraction-digits 2;            }
        description
            "Psu input power critical threshold minimum value";
        }

        leaf pin-critical-threshold-max {
            type  decimal64 {
                 fraction-digits 2;            }
        description
            "Psu input power critical threshold maximum value";
        }
    }

    notification psu-pin-low-alert-recovery {

        description "This notification is sent when input power of PSU exceeds a given threshold.";

        // severity "INFO";
        // eventClass "STATE";
        leaf name {
            type  string;
        description
            "References the component name";
        }

        leaf input-power {
            type  decimal64 {
                 fraction-digits 2;            }
        description
            "Input power of power supply";
        }

        leaf pin-alert-threshold-min {
            type  decimal64 {
                 fraction-digits 2;            }
        description
            "Psu input power alert threshold minimum value";
        }

        leaf pin-alert-threshold-max {
            type  decimal64 {
                 fraction-digits 2;            }
        description
            "Psu input power alert threshold maximum value";
        }
    }

    notification psu-pin-high-alert-recovery {

        description "This notification is sent when input power violation is recovered.";

        // severity "INFO";
        // eventClass "STATE";
        leaf name {
            type  string;
        description
            "References the component name";
        }

        leaf input-power {
            type  decimal64 {
                 fraction-digits 2;            }
        description
            "Input power of power supply";
        }

        leaf pin-alert-threshold-min {
            type  decimal64 {
                 fraction-digits 2;            }
        description
            "Psu input power alert threshold minimum value";
        }

        leaf pin-alert-threshold-max {
            type  decimal64 {
                 fraction-digits 2;            }
        description
            "Psu input power alert threshold maximum value";
        }
    }

    notification psu-pin-low-critical-recovery {

        description "This notification is sent when input power violation is recovered.";

        // severity "INFO";
        // eventClass "STATE";
        leaf name {
            type  string;
        description
            "References the component name";
        }

        leaf input-power {
            type  decimal64 {
                 fraction-digits 2;            }
        description
            "Input power of power supply";
        }

        leaf pin-critical-threshold-min {
            type  decimal64 {
                 fraction-digits 2;            }
        description
            "Psu input power critical threshold minimum value";
        }

        leaf pin-critical-threshold-max {
            type  decimal64 {
                 fraction-digits 2;            }
        description
            "Psu input power critical threshold maximum value";
        }
    }

    notification psu-pin-high-critical-recovery {

        description "This notification is sent when input power violation is recovered.";

        // severity "INFO";
        // eventClass "STATE";
        leaf name {
            type  string;
        description
            "References the component name";
        }

        leaf input-power {
            type  decimal64 {
                 fraction-digits 2;            }
        description
            "Input power of power supply";
        }

        leaf pin-critical-threshold-min {
            type  decimal64 {
                 fraction-digits 2;            }
        description
            "Psu input power critical threshold minimum value";
        }

        leaf pin-critical-threshold-max {
            type  decimal64 {
                 fraction-digits 2;            }
        description
            "Psu input power critical threshold maximum value";
        }
    }

    notification psu-pout-low-alert {

        description "This notification is sent when output power of PSU exceeds a given threshold.";

        // severity "CRITICAL";
        // eventClass "STATE";
        leaf name {
            type  string;
        description
            "References the component name";
        }

        leaf power-consumption {
            type  decimal64 {
                 fraction-digits 2;            }
        description
            "Output power of power supply";
        }

        leaf pout-alert-threshold-min {
            type  decimal64 {
                 fraction-digits 2;            }
        description
            "Psu output power alert threshold minimum value";
        }

        leaf pout-alert-threshold-max {
            type  decimal64 {
                 fraction-digits 2;            }
        description
            "Psu output power alert threshold maximum value";
        }
    }

    notification psu-pout-high-alert {

        description "This notification is sent when output power of PSU exceeds a given threshold.";

        // severity "CRITICAL";
        // eventClass "STATE";
        leaf name {
            type  string;
        description
            "References the component name";
        }

        leaf power-consumption {
            type  decimal64 {
                 fraction-digits 2;            }
        description
            "Output power of power supply";
        }

        leaf pout-alert-threshold-min {
            type  decimal64 {
                 fraction-digits 2;            }
        description
            "Psu output power alert threshold minimum value";
        }

        leaf pout-alert-threshold-max {
            type  decimal64 {
                 fraction-digits 2;            }
        description
            "Psu output power alert threshold maximum value";
        }
    }

    notification psu-pout-low-critical {

        description "This notification is sent when output power of PSU exceeds a given threshold.";

        // severity "CRITICAL";
        // eventClass "STATE";
        leaf name {
            type  string;
        description
            "References the component name";
        }

        leaf power-consumption {
            type  decimal64 {
                 fraction-digits 2;            }
        description
            "Output power of power supply";
        }

        leaf pout-critical-threshold-min {
            type  decimal64 {
                 fraction-digits 2;            }
        description
            "Psu output power critical threshold minimum value";
        }

        leaf pout-critical-threshold-max {
            type  decimal64 {
                 fraction-digits 2;            }
        description
            "Psu output power critical threshold maximum value";
        }
    }

    notification psu-pout-high-critical {

        description "This notification is sent when output power of PSU exceeds a given threshold.";

        // severity "CRITICAL";
        // eventClass "STATE";
        leaf name {
            type  string;
        description
            "References the component name";
        }

        leaf power-consumption {
            type  decimal64 {
                 fraction-digits 2;            }
        description
            "Output power of power supply";
        }

        leaf pout-critical-threshold-min {
            type  decimal64 {
                 fraction-digits 2;            }
        description
            "Psu output power critical threshold minimum value";
        }

        leaf pout-critical-threshold-max {
            type  decimal64 {
                 fraction-digits 2;            }
        description
            "Psu output power critical threshold maximum value";
        }
    }

    notification psu-pout-low-alert-recovery {

        description "This notification is sent when output power of PSU exceeds a given threshold.";

        // severity "INFO";
        // eventClass "STATE";
        leaf name {
            type  string;
        description
            "References the component name";
        }

        leaf power-consumption {
            type  decimal64 {
                 fraction-digits 2;            }
        description
            "Output power of power supply";
        }

        leaf pout-alert-threshold-min {
            type  decimal64 {
                 fraction-digits 2;            }
        description
            "Psu output power alert threshold minimum value";
        }

        leaf pout-alert-threshold-max {
            type  decimal64 {
                 fraction-digits 2;            }
        description
            "Psu output power alert threshold maximum value";
        }
    }

    notification psu-pout-high-alert-recovery {

        description "This notification is sent when output power violation is recovered.";

        // severity "INFO";
        // eventClass "STATE";
        leaf name {
            type  string;
        description
            "References the component name";
        }

        leaf power-consumption {
            type  decimal64 {
                 fraction-digits 2;            }
        description
            "Output power of power supply";
        }

        leaf pout-alert-threshold-min {
            type  decimal64 {
                 fraction-digits 2;            }
        description
            "Psu output power alert threshold minimum value";
        }

        leaf pout-alert-threshold-max {
            type  decimal64 {
                 fraction-digits 2;            }
        description
            "Psu output power alert threshold maximum value";
        }
    }

    notification psu-pout-low-critical-recovery {

        description "This notification is sent when output power violation is recovered.";

        // severity "INFO";
        // eventClass "STATE";
        leaf name {
            type  string;
        description
            "References the component name";
        }

        leaf power-consumption {
            type  decimal64 {
                 fraction-digits 2;            }
        description
            "Output power of power supply";
        }

        leaf pout-critical-threshold-min {
            type  decimal64 {
                 fraction-digits 2;            }
        description
            "Psu output power critical threshold minimum value";
        }

        leaf pout-critical-threshold-max {
            type  decimal64 {
                 fraction-digits 2;            }
        description
            "Psu output power critical threshold maximum value";
        }
    }

    notification psu-pout-high-critical-recovery {

        description "This notification is sent when output power violation is recovered.";

        // severity "INFO";
        // eventClass "STATE";
        leaf name {
            type  string;
        description
            "References the component name";
        }

        leaf power-consumption {
            type  decimal64 {
                 fraction-digits 2;            }
        description
            "Output power of power supply";
        }

        leaf pout-critical-threshold-min {
            type  decimal64 {
                 fraction-digits 2;            }
        description
            "Psu output power critical threshold minimum value";
        }

        leaf pout-critical-threshold-max {
            type  decimal64 {
                 fraction-digits 2;            }
        description
            "Psu output power critical threshold maximum value";
        }
    }

    notification psu-iout-low-alert {

        description "This notification is sent when output current of PSU exceeds a given threshold.";

        // severity "CRITICAL";
        // eventClass "STATE";
        leaf name {
            type  string;
        description
            "References the component name";
        }

        leaf output-current {
            type  decimal64 {
                 fraction-digits 2;            }
        description
            "Output current of power supply";
        }

        leaf iout-alert-threshold-min {
            type  decimal64 {
                 fraction-digits 2;            }
        description
            "Psu output current alert threshold minimum value";
        }

        leaf iout-alert-threshold-max {
            type  decimal64 {
                 fraction-digits 2;            }
        description
            "Psu output current alert threshold maximum value";
        }
    }

    notification psu-iout-high-alert {

        description "This notification is sent when output current of PSU exceeds a given threshold.";

        // severity "CRITICAL";
        // eventClass "STATE";
        leaf name {
            type  string;
        description
            "References the component name";
        }

        leaf output-current {
            type  decimal64 {
                 fraction-digits 2;            }
        description
            "Output current of power supply";
        }

        leaf iout-alert-threshold-min {
            type  decimal64 {
                 fraction-digits 2;            }
        description
            "Psu output current alert threshold minimum value";
        }

        leaf iout-alert-threshold-max {
            type  decimal64 {
                 fraction-digits 2;            }
        description
            "Psu output current alert threshold maximum value";
        }
    }

    notification psu-iout-low-critical {

        description "This notification is sent when output current of PSU exceeds a given threshold.";

        // severity "CRITICAL";
        // eventClass "STATE";
        leaf name {
            type  string;
        description
            "References the component name";
        }

        leaf output-current {
            type  decimal64 {
                 fraction-digits 2;            }
        description
            "Output current of power supply";
        }

        leaf iout-critical-threshold-min {
            type  decimal64 {
                 fraction-digits 2;            }
        description
            "Psu output current critical threshold minimum value";
        }

        leaf iout-critical-threshold-max {
            type  decimal64 {
                 fraction-digits 2;            }
        description
            "Psu output current critical threshold maximum value";
        }
    }

    notification psu-iout-high-critical {

        description "This notification is sent when output current of PSU exceeds a given threshold.";

        // severity "CRITICAL";
        // eventClass "STATE";
        leaf name {
            type  string;
        description
            "References the component name";
        }

        leaf output-current {
            type  decimal64 {
                 fraction-digits 2;            }
        description
            "Output current of power supply";
        }

        leaf iout-critical-threshold-min {
            type  decimal64 {
                 fraction-digits 2;            }
        description
            "Psu output current critical threshold minimum value";
        }

        leaf iout-critical-threshold-max {
            type  decimal64 {
                 fraction-digits 2;            }
        description
            "Psu output current critical threshold maximum value";
        }
    }

    notification psu-iout-low-alert-recovery {

        description "This notification is sent when output current of PSU exceeds a given threshold.";

        // severity "INFO";
        // eventClass "STATE";
        leaf name {
            type  string;
        description
            "References the component name";
        }

        leaf output-current {
            type  decimal64 {
                 fraction-digits 2;            }
        description
            "Output current of power supply";
        }

        leaf iout-alert-threshold-min {
            type  decimal64 {
                 fraction-digits 2;            }
        description
            "Psu output current alert threshold minimum value";
        }

        leaf iout-alert-threshold-max {
            type  decimal64 {
                 fraction-digits 2;            }
        description
            "Psu output current alert threshold maximum value";
        }
    }

    notification psu-iout-high-alert-recovery {

        description "This notification is sent when output current violation is recovered.";

        // severity "INFO";
        // eventClass "STATE";
        leaf name {
            type  string;
        description
            "References the component name";
        }

        leaf output-current {
            type  decimal64 {
                 fraction-digits 2;            }
        description
            "Output current of power supply";
        }

        leaf iout-alert-threshold-min {
            type  decimal64 {
                 fraction-digits 2;            }
        description
            "Psu output current alert threshold minimum value";
        }

        leaf iout-alert-threshold-max {
            type  decimal64 {
                 fraction-digits 2;            }
        description
            "Psu output current alert threshold maximum value";
        }
    }

    notification psu-iout-low-critical-recovery {

        description "This notification is sent when output current violation is recovered.";

        // severity "INFO";
        // eventClass "STATE";
        leaf name {
            type  string;
        description
            "References the component name";
        }

        leaf output-current {
            type  decimal64 {
                 fraction-digits 2;            }
        description
            "Output current of power supply";
        }

        leaf iout-critical-threshold-min {
            type  decimal64 {
                 fraction-digits 2;            }
        description
            "Psu output current critical threshold minimum value";
        }

        leaf iout-critical-threshold-max {
            type  decimal64 {
                 fraction-digits 2;            }
        description
            "Psu output current critical threshold maximum value";
        }
    }

    notification psu-iout-high-critical-recovery {

        description "This notification is sent when output current violation is recovered.";

        // severity "INFO";
        // eventClass "STATE";
        leaf name {
            type  string;
        description
            "References the component name";
        }

        leaf output-current {
            type  decimal64 {
                 fraction-digits 2;            }
        description
            "Output current of power supply";
        }

        leaf iout-critical-threshold-min {
            type  decimal64 {
                 fraction-digits 2;            }
        description
            "Psu output current critical threshold minimum value";
        }

        leaf iout-critical-threshold-max {
            type  decimal64 {
                 fraction-digits 2;            }
        description
            "Psu output current critical threshold maximum value";
        }
    }

    notification psu-iin-low-alert {

        description "This notification is sent when input current of PSU exceeds a given threshold.";

        // severity "CRITICAL";
        // eventClass "STATE";
        leaf name {
            type  string;
        description
            "References the component name";
        }

        leaf input-current {
            type  decimal64 {
                 fraction-digits 2;            }
        description
            "Input current of power supply";
        }

        leaf iin-alert-threshold-min {
            type  decimal64 {
                 fraction-digits 2;            }
        description
            "Psu input current alert threshold minimum value";
        }

        leaf iin-alert-threshold-max {
            type  decimal64 {
                 fraction-digits 2;            }
        description
            "Psu input current alert threshold maximum value";
        }
    }

    notification psu-iin-high-alert {

        description "This notification is sent when input current of PSU exceeds a given threshold.";

        // severity "CRITICAL";
        // eventClass "STATE";
        leaf name {
            type  string;
        description
            "References the component name";
        }

        leaf input-current {
            type  decimal64 {
                 fraction-digits 2;            }
        description
            "Input current of power supply";
        }

        leaf iin-alert-threshold-min {
            type  decimal64 {
                 fraction-digits 2;            }
        description
            "Psu input current alert threshold minimum value";
        }

        leaf iin-alert-threshold-max {
            type  decimal64 {
                 fraction-digits 2;            }
        description
            "Psu input current alert threshold maximum value";
        }
    }

    notification psu-iin-low-critical {

        description "This notification is sent when input current of PSU exceeds a given threshold.";

        // severity "CRITICAL";
        // eventClass "STATE";
        leaf name {
            type  string;
        description
            "References the component name";
        }

        leaf input-current {
            type  decimal64 {
                 fraction-digits 2;            }
        description
            "Input current of power supply";
        }

        leaf iin-critical-threshold-min {
            type  decimal64 {
                 fraction-digits 2;            }
        description
            "Psu input current critical threshold minimum value";
        }

        leaf iin-critical-threshold-max {
            type  decimal64 {
                 fraction-digits 2;            }
        description
            "Psu input current critical threshold maximum value";
        }
    }

    notification psu-iin-high-critical {

        description "This notification is sent when input current of PSU exceeds a given threshold.";

        // severity "CRITICAL";
        // eventClass "STATE";
        leaf name {
            type  string;
        description
            "References the component name";
        }

        leaf input-current {
            type  decimal64 {
                 fraction-digits 2;            }
        description
            "Input current of power supply";
        }

        leaf iin-critical-threshold-min {
            type  decimal64 {
                 fraction-digits 2;            }
        description
            "Psu input current critical threshold minimum value";
        }

        leaf iin-critical-threshold-max {
            type  decimal64 {
                 fraction-digits 2;            }
        description
            "Psu input current critical threshold maximum value";
        }
    }

    notification psu-iin-low-alert-recovery {

        description "This notification is sent when input current of PSU exceeds a given threshold.";

        // severity "INFO";
        // eventClass "STATE";
        leaf name {
            type  string;
        description
            "References the component name";
        }

        leaf input-current {
            type  decimal64 {
                 fraction-digits 2;            }
        description
            "Input current of power supply";
        }

        leaf iin-alert-threshold-min {
            type  decimal64 {
                 fraction-digits 2;            }
        description
            "Psu input current alert threshold minimum value";
        }

        leaf iin-alert-threshold-max {
            type  decimal64 {
                 fraction-digits 2;            }
        description
            "Psu input current alert threshold maximum value";
        }
    }

    notification psu-iin-high-alert-recovery {

        description "This notification is sent when input current violation is recovered.";

        // severity "INFO";
        // eventClass "STATE";
        leaf name {
            type  string;
        description
            "References the component name";
        }

        leaf input-current {
            type  decimal64 {
                 fraction-digits 2;            }
        description
            "Input current of power supply";
        }

        leaf iin-alert-threshold-min {
            type  decimal64 {
                 fraction-digits 2;            }
        description
            "Psu input current alert threshold minimum value";
        }

        leaf iin-alert-threshold-max {
            type  decimal64 {
                 fraction-digits 2;            }
        description
            "Psu input current alert threshold maximum value";
        }
    }

    notification psu-iin-low-critical-recovery {

        description "This notification is sent when input current violation is recovered.";

        // severity "INFO";
        // eventClass "STATE";
        leaf name {
            type  string;
        description
            "References the component name";
        }

        leaf input-current {
            type  decimal64 {
                 fraction-digits 2;            }
        description
            "Input current of power supply";
        }

        leaf iin-critical-threshold-min {
            type  decimal64 {
                 fraction-digits 2;            }
        description
            "Psu input current critical threshold minimum value";
        }

        leaf iin-critical-threshold-max {
            type  decimal64 {
                 fraction-digits 2;            }
        description
            "Psu input current critical threshold maximum value";
        }
    }

    notification psu-iin-high-critical-recovery {

        description "This notification is sent when input current violation is recovered.";

        // severity "INFO";
        // eventClass "STATE";
        leaf name {
            type  string;
        description
            "References the component name";
        }

        leaf input-current {
            type  decimal64 {
                 fraction-digits 2;            }
        description
            "Input current of power supply";
        }

        leaf iin-critical-threshold-min {
            type  decimal64 {
                 fraction-digits 2;            }
        description
            "Psu input current critical threshold minimum value";
        }

        leaf iin-critical-threshold-max {
            type  decimal64 {
                 fraction-digits 2;            }
        description
            "Psu input current critical threshold maximum value";
        }
    }

    notification psu-temp1-low-alert {

        description "This notification is sent when temp1 of PSU exceeds a given threshold.";

        // severity "CRITICAL";
        // eventClass "STATE";
        leaf name {
            type  string;
        description
            "References the component name";
        }

        leaf temperature-sensor1 {
            type  decimal64 {
                 fraction-digits 2;            }
        description
            "Temperature of power supply sensor 1";
        }

        leaf temp1-alert-threshold-min {
            type  decimal64 {
                 fraction-digits 2;            }
        description
            "Psu temperature 1 alert threshold minimum value";
        }

        leaf temp1-alert-threshold-max {
            type  decimal64 {
                 fraction-digits 2;            }
        description
            "Psu temperature 1 alert threshold maximum value";
        }
    }

    notification psu-temp1-high-alert {

        description "This notification is sent when temp1 of PSU exceeds a given threshold.";

        // severity "CRITICAL";
        // eventClass "STATE";
        leaf name {
            type  string;
        description
            "References the component name";
        }

        leaf temperature-sensor1 {
            type  decimal64 {
                 fraction-digits 2;            }
        description
            "Temperature of power supply sensor 1";
        }

        leaf temp1-alert-threshold-min {
            type  decimal64 {
                 fraction-digits 2;            }
        description
            "Psu temperature 1 alert threshold minimum value";
        }

        leaf temp1-alert-threshold-max {
            type  decimal64 {
                 fraction-digits 2;            }
        description
            "Psu temperature 1 alert threshold maximum value";
        }
    }

    notification psu-temp1-low-critical {

        description "This notification is sent when temp1 of PSU exceeds a given threshold.";

        // severity "CRITICAL";
        // eventClass "STATE";
        leaf name {
            type  string;
        description
            "References the component name";
        }

        leaf temperature-sensor1 {
            type  decimal64 {
                 fraction-digits 2;            }
        description
            "Temperature of power supply sensor 1";
        }

        leaf temp1-critical-threshold-min {
            type  decimal64 {
                 fraction-digits 2;            }
        description
            "Psu temperature 1 critical threshold minimum value";
        }

        leaf temp1-critical-threshold-max {
            type  decimal64 {
                 fraction-digits 2;            }
        description
            "Psu temperature 1 critical threshold maximum value";
        }
    }

    notification psu-temp1-high-critical {

        description "This notification is sent when temp1 of PSU exceeds a given threshold.";

        // severity "CRITICAL";
        // eventClass "STATE";
        leaf name {
            type  string;
        description
            "References the component name";
        }

        leaf temperature-sensor1 {
            type  decimal64 {
                 fraction-digits 2;            }
        description
            "Temperature of power supply sensor 1";
        }

        leaf temp1-critical-threshold-min {
            type  decimal64 {
                 fraction-digits 2;            }
        description
            "Psu temperature 1 critical threshold minimum value";
        }

        leaf temp1-critical-threshold-max {
            type  decimal64 {
                 fraction-digits 2;            }
        description
            "Psu temperature 1 critical threshold maximum value";
        }
    }

    notification psu-temp1-low-alert-recovery {

        description "This notification is sent when temp1 of PSU exceeds a given threshold.";

        // severity "INFO";
        // eventClass "STATE";
        leaf name {
            type  string;
        description
            "References the component name";
        }

        leaf temperature-sensor1 {
            type  decimal64 {
                 fraction-digits 2;            }
        description
            "Temperature of power supply sensor 1";
        }

        leaf temp1-alert-threshold-min {
            type  decimal64 {
                 fraction-digits 2;            }
        description
            "Psu temperature 1 alert threshold minimum value";
        }

        leaf temp1-alert-threshold-max {
            type  decimal64 {
                 fraction-digits 2;            }
        description
            "Psu temperature 1 alert threshold maximum value";
        }
    }

    notification psu-temp1-high-alert-recovery {

        description "This notification is sent when temp1 violation is recovered.";

        // severity "INFO";
        // eventClass "STATE";
        leaf name {
            type  string;
        description
            "References the component name";
        }

        leaf temperature-sensor1 {
            type  decimal64 {
                 fraction-digits 2;            }
        description
            "Temperature of power supply sensor 1";
        }

        leaf temp1-alert-threshold-min {
            type  decimal64 {
                 fraction-digits 2;            }
        description
            "Psu temperature 1 alert threshold minimum value";
        }

        leaf temp1-alert-threshold-max {
            type  decimal64 {
                 fraction-digits 2;            }
        description
            "Psu temperature 1 alert threshold maximum value";
        }
    }

    notification psu-temp1-low-critical-recovery {

        description "This notification is sent when temp1 violation is recovered.";

        // severity "INFO";
        // eventClass "STATE";
        leaf name {
            type  string;
        description
            "References the component name";
        }

        leaf temperature-sensor1 {
            type  decimal64 {
                 fraction-digits 2;            }
        description
            "Temperature of power supply sensor 1";
        }

        leaf temp1-critical-threshold-min {
            type  decimal64 {
                 fraction-digits 2;            }
        description
            "Psu temperature 1 critical threshold minimum value";
        }

        leaf temp1-critical-threshold-max {
            type  decimal64 {
                 fraction-digits 2;            }
        description
            "Psu temperature 1 critical threshold maximum value";
        }
    }

    notification psu-temp1-high-critical-recovery {

        description "This notification is sent when temp1 violation is recovered.";

        // severity "INFO";
        // eventClass "STATE";
        leaf name {
            type  string;
        description
            "References the component name";
        }

        leaf temperature-sensor1 {
            type  decimal64 {
                 fraction-digits 2;            }
        description
            "Temperature of power supply sensor 1";
        }

        leaf temp1-critical-threshold-min {
            type  decimal64 {
                 fraction-digits 2;            }
        description
            "Psu temperature 1 critical threshold minimum value";
        }

        leaf temp1-critical-threshold-max {
            type  decimal64 {
                 fraction-digits 2;            }
        description
            "Psu temperature 1 critical threshold maximum value";
        }
    }

    notification psu-temp2-low-alert {

        description "This notification is sent when input voltage of PSU exceeds a given threshold.";

        // severity "CRITICAL";
        // eventClass "STATE";
        leaf name {
            type  string;
        description
            "References the component name";
        }

        leaf temperature-sensor2 {
            type  decimal64 {
                 fraction-digits 2;            }
        description
            "Temperature of power supply sensor 2";
        }

        leaf temp2-alert-threshold-min {
            type  decimal64 {
                 fraction-digits 2;            }
        description
            "Psu temperature 2 alert threshold minimum value";
        }

        leaf temp2-alert-threshold-max {
            type  decimal64 {
                 fraction-digits 2;            }
        description
            "Psu temperature 2 alert threshold maximum value";
        }
    }

    notification psu-temp2-high-alert {

        description "This notification is sent when input voltage of PSU exceeds a given threshold.";

        // severity "CRITICAL";
        // eventClass "STATE";
        leaf name {
            type  string;
        description
            "References the component name";
        }

        leaf temperature-sensor2 {
            type  decimal64 {
                 fraction-digits 2;            }
        description
            "Temperature of power supply sensor 2";
        }

        leaf temp2-alert-threshold-min {
            type  decimal64 {
                 fraction-digits 2;            }
        description
            "Psu temperature 2 alert threshold minimum value";
        }

        leaf temp2-alert-threshold-max {
            type  decimal64 {
                 fraction-digits 2;            }
        description
            "Psu temperature 2 alert threshold maximum value";
        }
    }

    notification psu-temp2-low-critical {

        description "This notification is sent when input voltage of PSU exceeds a given threshold.";

        // severity "CRITICAL";
        // eventClass "STATE";
        leaf name {
            type  string;
        description
            "References the component name";
        }

        leaf temperature-sensor2 {
            type  decimal64 {
                 fraction-digits 2;            }
        description
            "Temperature of power supply sensor 2";
        }

        leaf temp2-critical-threshold-min {
            type  decimal64 {
                 fraction-digits 2;            }
        description
            "Psu temperature 2 critical threshold minimum value";
        }

        leaf temp2-critical-threshold-max {
            type  decimal64 {
                 fraction-digits 2;            }
        description
            "Psu temperature 2 critical threshold maximum value";
        }
    }

    notification psu-temp2-high-critical {

        description "This notification is sent when input voltage of PSU exceeds a given threshold.";

        // severity "CRITICAL";
        // eventClass "STATE";
        leaf name {
            type  string;
        description
            "References the component name";
        }

        leaf temperature-sensor2 {
            type  decimal64 {
                 fraction-digits 2;            }
        description
            "Temperature of power supply sensor 2";
        }

        leaf temp2-critical-threshold-min {
            type  decimal64 {
                 fraction-digits 2;            }
        description
            "Psu temperature 2 critical threshold minimum value";
        }

        leaf temp2-critical-threshold-max {
            type  decimal64 {
                 fraction-digits 2;            }
        description
            "Psu temperature 2 critical threshold maximum value";
        }
    }

    notification psu-temp2-low-alert-recovery {

        description "This notification is sent when input voltage of PSU exceeds a given threshold.";

        // severity "INFO";
        // eventClass "STATE";
        leaf name {
            type  string;
        description
            "References the component name";
        }

        leaf temperature-sensor2 {
            type  decimal64 {
                 fraction-digits 2;            }
        description
            "Temperature of power supply sensor 2";
        }

        leaf temp2-alert-threshold-min {
            type  decimal64 {
                 fraction-digits 2;            }
        description
            "Psu temperature 2 alert threshold minimum value";
        }

        leaf temp2-alert-threshold-max {
            type  decimal64 {
                 fraction-digits 2;            }
        description
            "Psu temperature 2 alert threshold maximum value";
        }
    }

    notification psu-temp2-high-alert-recovery {

        description "This notification is sent when input voltage of PSU exceeds a given threshold.";

        // severity "INFO";
        // eventClass "STATE";
        leaf name {
            type  string;
        description
            "References the component name";
        }

        leaf temperature-sensor2 {
            type  decimal64 {
                 fraction-digits 2;            }
        description
            "Temperature of power supply sensor 2";
        }

        leaf temp2-alert-threshold-min {
            type  decimal64 {
                 fraction-digits 2;            }
        description
            "Psu temperature 2 alert threshold minimum value";
        }

        leaf temp2-alert-threshold-max {
            type  decimal64 {
                 fraction-digits 2;            }
        description
            "Psu temperature 2 alert threshold maximum value";
        }
    }

    notification psu-temp2-low-critical-recovery {

        description "This notification is sent when input voltage of PSU exceeds a given threshold.";

        // severity "INFO";
        // eventClass "STATE";
        leaf name {
            type  string;
        description
            "References the component name";
        }

        leaf temperature-sensor2 {
            type  decimal64 {
                 fraction-digits 2;            }
        description
            "Temperature of power supply sensor 2";
        }

        leaf temp2-critical-threshold-min {
            type  decimal64 {
                 fraction-digits 2;            }
        description
            "Psu temperature 2 critical threshold minimum value";
        }

        leaf temp2-critical-threshold-max {
            type  decimal64 {
                 fraction-digits 2;            }
        description
            "Psu temperature 2 critical threshold maximum value";
        }
    }

    notification psu-temp2-high-critical-recovery {

        description "This notification is sent when input voltage of PSU exceeds a given threshold.";

        // severity "INFO";
        // eventClass "STATE";
        leaf name {
            type  string;
        description
            "References the component name";
        }

        leaf temperature-sensor2 {
            type  decimal64 {
                 fraction-digits 2;            }
        description
            "Temperature of power supply sensor 2";
        }

        leaf temp2-critical-threshold-min {
            type  decimal64 {
                 fraction-digits 2;            }
        description
            "Psu temperature 2 critical threshold minimum value";
        }

        leaf temp2-critical-threshold-max {
            type  decimal64 {
                 fraction-digits 2;            }
        description
            "Psu temperature 2 critical threshold maximum value";
        }
    }

    notification fan-status-alarm {

        description "This notification is sent when fan is in alarm state.";

        // severity "CRITICAL";
        // eventClass "STATE";
        leaf name {
            type  string;
        description
            "References the component name";
        }

        leaf fan-index {
            type  uint8;
        description
            "Fan identifier index in the system";
        }

        leaf fan-status {
            type  cml_cmm_fan_status_t;
        description
            "The status of the fan";
        }
    }

    notification fan-status-alarm-recovery {

        description "This notification is sent when fan recovers from an alarm state.";

        // severity "INFO";
        // eventClass "STATE";
        leaf name {
            type  string;
        description
            "References the component name";
        }

        leaf fan-index {
            type  uint8;
        description
            "Fan identifier index in the system";
        }

        leaf fan-status {
            type  cml_cmm_fan_status_t;
        description
            "The status of the fan";
        }
    }

    notification fan-rpm-min-alert {

        description "This notification is sent when fan RPM set to its minimum value..";

        // severity "CRITICAL";
        // eventClass "STATE";
        leaf name {
            type  string;
        description
            "References the component name";
        }

        leaf minimum-rpm {
            type  uint32;
        description
            "Value represents the minimum supported RPM of fan";
        }
    }

    notification fan-rpm-max-alert {

        description "This notification is sent when fan RPM set to its maximum value..";

        // severity "CRITICAL";
        // eventClass "STATE";
        leaf name {
            type  string;
        description
            "References the component name";
        }

        leaf maximum-rpm {
            type  uint32;
        description
            "Value represents the maximum supported RPM of fan";
        }
    }

    notification fan-tray-inserted {

        description "This notification is sent when fan tray is inserted.";

        // severity "WARNING";
        // eventClass "STATE";
        leaf name {
            type  string;
        description
            "References the component name";
        }
    }

    notification fan-tray-removed {

        description "This notification is sent when fan tray is removed.";

        // severity "WARNING";
        // eventClass "STATE";
        leaf name {
            type  string;
        description
            "References the component name";
        }
    }

    notification hardware-tcam-util-warning-notification {

        description "This notification is generated when number of entries in TCAM group crosses the warning threshold limit..";

        // severity "WARNING";
        // eventClass "STATE";
        leaf group-id {
            type  uint32;
        description
            "A unique number corresponding to each TCAM group. This attribute is
                    used solely for defining the key for the TCAM utilization filter
                    groups object list. It's value shouldn't be interpreted.";
        }

        leaf group-name {
            type cml-data-types:cml_line_t;
        description
            "TCAM Utilization filter group name.";
        }

        leaf used-percentage {
            type  int32;
        description
            "Percentage of entries used in the TCAM group. Value of -1 means the
                    field is not applicable.";
        }

        leaf free-entries {
            type  int32;
        description
            "Count of free entries in the TCAM group. Value of -1 means the field
                    is not applicable.";
        }
    }

    notification hardware-tcam-util-critical-notification {

        description "This notification is generated when number of entries in TCAM group crosses the critical threshold limit..";

        // severity "CRITICAL";
        // eventClass "STATE";
        leaf group-id {
            type  uint32;
        description
            "A unique number corresponding to each TCAM group. This attribute is
                    used solely for defining the key for the TCAM utilization filter
                    groups object list. It's value shouldn't be interpreted.";
        }

        leaf group-name {
            type cml-data-types:cml_line_t;
        description
            "TCAM Utilization filter group name.";
        }

        leaf used-percentage {
            type  int32;
        description
            "Percentage of entries used in the TCAM group. Value of -1 means the
                    field is not applicable.";
        }

        leaf free-entries {
            type  int32;
        description
            "Count of free entries in the TCAM group. Value of -1 means the field
                    is not applicable.";
        }
    }

}

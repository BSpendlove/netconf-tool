/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-watchdog.yang
*
*/

module ipi-watchdog {

    yang-version 1.1;

    namespace   "http://www.ipinfusion.com/yang/ocnos/ipi-watchdog";

    prefix "ipi-watchdog";

    import ietf-yang-types {
        prefix yang;
        revision-date 2013-07-15;
    }

    import cml-data-types {
        prefix cml-data-types;
        revision-date 2022-04-04;
    }

    import ipi-watchdog-types {
        prefix ipi-watchdog-types;
        revision-date 2021-11-30;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "This module manages protocol processes status and watchdogs";


    revision "2021-11-30" {
        description "Attribute watchdog-status changed to watchdog-status-disabled";
        reference " 0.1.4.";
    }

    revision "2021-11-08" {
        description "Fix the watchdog process state to display runtime information about all process";
        reference " 0.1.3.";
    }

    revision "2021-10-11" {
        description "Attribute watchdog-enable changed to watchdog-disabled";
        reference " 0.1.2.";
    }

    revision "2021-08-09" {
        description "Some attributes of watchdog-modules-process-state changed name and type";
        reference " 0.1.1.";
    }

    revision "2021-07-30" {
        description "PSERV restructured";
        reference " 0.1.0.";
    }

    grouping watchdog-modules-process-state {
        description
            "watchdogCMLSEPmodulesCMLSEPprocessCMLSEPstate";
        leaf process-name  {
            type  ipi-watchdog-types:watchdog_module_name_t;
            description "Protocol module identification.";
        } // END of process-name definition.

        leaf process-status  {
            type  ipi-watchdog-types:watchdog_process_status_t;
            description "Process state.";
        } // END of process-status definition.

        leaf start-time  {
            type  yang:date-and-time {
                pattern "\\d{4}-\\d{2}-\\d{2}T\\d{2}:\\d{2}:\\d{2}(\\.\\d+)?(Z|[\\+\\-]\\d{2}:\\d{2})";
                }
                description "Starting time of a protocol module.";
            } // END of start-time definition.

            leaf down-reason  {
                type  cml-data-types:cml_line_t {
                    length "1..1965";
                }
                description "Reason for process to shutdown. This value will be the signal
                            description.";
            } // END of down-reason definition.

    } // END of watchdog-modules-process-state definition.
    grouping watchdog-modules-process-top {
        description
            "watchdogCMLSEPmodulesCMLSEPprocessCMLSEPtop";
        container process {
            description
                "Container for process state data";
            container state {
                config false;
                description
                    "Operational state data";
                uses watchdog-modules-process-state;
            } // END of state-container definition.
        } // END of process-container definition.
    } // END of watchdog-modules-process-top definition.
    grouping watchdog-modules-config {
        description
            "watchdogCMLSEPmodulesCMLSEPconfig";
        leaf name  {
            type  ipi-watchdog-types:watchdog_module_name_t;
            description "Enable software watchdog functionality for a particular software
                        module.";
        } // END of name definition.

        leaf module-watchdog-status-disabled  {
            type  empty;
            mandatory true;
            description "Enable software watchdog functionality for a particular software
                        module.";
        } // END of module-watchdog-status-disabled definition.

    } // END of watchdog-modules-config definition.
    grouping watchdog-modules-top {
        description
            "watchdogCMLSEPmodulesCMLSEPtop";
        container software-modules {
            description
                "Container for modules watchdogs";

            list software-module {
            when " not(/ipi-watchdog:watchdog/ipi-watchdog:config/ipi-watchdog:watchdog-disabled) ";
                key "name";
                description
                    "List of modules";
                leaf name  {
                    type  leafref {
                        path  "../config/name";
                    }
                    description "Enable software watchdog functionality for a particular software
                                module.";
                } // END of name definition.

                container config {
                    description
                        "Container for module watchdog configuration";
                    uses watchdog-modules-config;
                } // END of config-container definition.
                container state {
                    config false;
                    description
                        "Operational state data";
                    uses watchdog-modules-config;
                } // END of state-container definition.
                uses watchdog-modules-process-top;
            } // End of software-module-list
        } // END of software-modules-container definition.
    } // END of watchdog-modules-top definition.
    grouping watchdog-config {
        description
            "watchdogCMLSEPconfig";
        leaf watchdog-disabled  {
            type  empty;
            description "Disable software watchdog functionality for all modules. This feature
                        is enabled by default.";
        } // END of watchdog-disabled definition.

        leaf keepalive-interval  {
            when " not(/ipi-watchdog:watchdog/ipi-watchdog:config/ipi-watchdog:watchdog-disabled) ";
            type  uint16 {
                 range "30..1800"  {
                    description "30..1800:Time in seconds";
                 }
            }
            default "60";
            description "Software watchdog keep-alive time interval in seconds. Default value
                        is 60 seconds.";
        } // END of keepalive-interval definition.

    } // END of watchdog-config definition.
    grouping watchdog-state {
        description
            "watchdogCMLSEPstate";
        leaf watchdog-status  {
            type  ipi-watchdog-types:watchdog_status_t;
            description "Status of software watchdog monitoring. If enabled, software watchdog
                        is active and is monitoring software anomalies for modules.";
        } // END of watchdog-status definition.

        leaf all-processes-status  {
            type  ipi-watchdog-types:watchdog_global_processes_status_t;
            description "Global process status of all modules. If all process are running, this
                        value will be true. Otherwise it wil be false.";
        } // END of all-processes-status definition.

    } // END of watchdog-state definition.
    grouping watchdog-top {
        description
            "watchdogCMLSEPtop";
        container config {
            description
                "Container for watchdog configuration";
            uses watchdog-config;
        } // END of config-container definition.
        container state {
            config false;
            description
                "Operational state data";
            uses watchdog-config;
            uses watchdog-state;
        } // END of state-container definition.
    } // END of watchdog-top definition.

    grouping  watchdog-grouping {
    description
        "Container for module watchdog";
    container watchdog {
        if-feature feature-list:HAVE_PSERVD;
        description
            "Container for module watchdog";
        uses watchdog-top;
        uses watchdog-modules-top;
    } // END of watchdog-container definition.
    } // END of watchdog-grouping definition.

    uses watchdog-grouping;

    rpc clear-core-dump {
        description "Clear core-dump files";
        input  {
            leaf core-dump  {
                type string;
                mandatory true;
                description "Core-dump filename";
            }
        }
    }

    notification protocol-module-down {

        description "protocol-module-down event is generated when a protocol module crashes..";

        // severity "CRITICAL";
        // eventClass "STATE";
        leaf name {
            type ipi-watchdog-types:watchdog_module_name_t;
        description
            "Enable software watchdog functionality for a particular software
                    module.";
        }

        leaf process-name {
            type ipi-watchdog-types:watchdog_module_name_t;
        description
            "Protocol module identification.";
        }

        leaf down-reason {
            type cml-data-types:cml_line_t;
        description
            "Reason for process to shutdown. This value will be the signal
                    description.";
        }
    }

    notification protocol-module-restarted {

        description "protocol-module-restarted event is generated when a protocol module recovers from down state..";

        // severity "MINOR";
        // eventClass "STATE";
        leaf name {
            type ipi-watchdog-types:watchdog_module_name_t;
        description
            "Enable software watchdog functionality for a particular software
                    module.";
        }

        leaf process-name {
            type ipi-watchdog-types:watchdog_module_name_t;
        description
            "Protocol module identification.";
        }

        leaf start-time {
            type  yang:date-and-time;
        description
            "Starting time of a protocol module.";
        }
    }

}

/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-sr-types.yang
*
*/

module ipi-sr-types {

    yang-version 1.1;

    namespace   "http://www.ipinfusion.com/yang/ocnos/ipi-sr-types";

    prefix "ipi-sr-types";

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-sr-types";


    revision "2021-09-03" {
        description "Update descriptions of attribute";
        reference "Initial Version";
    }

    revision "2021-02-28" {
        description "Adding support for SR Policy runtime attributes";
        reference " 0.4.0.";
    }

    revision "2020-12-15" {
        description "Change to have data-types in lower case instead of camel case";
        reference " 0.2.0.";
    }

    revision "2020-06-11" {
        description "Initial Version";
        reference " 0.1.0.";
    }



    typedef  sr_sid_value_type_t {
        type enumeration {
            enum index {
                value 1;
                description "Prefix-SID index";
            }
            enum absolute {
                value 2;
                description "Prefix-SID absolute value";
            }
        }
        description "type definition for SR_SID_VALUE_TYPE_T";
    }

    typedef  srte_segment_type_t {
        type enumeration {
            enum segment-type-1 {
                value 1;
                description "Segment-descriptor type: SR-MPLS Label";
            }
        }
        description "type definition for SRTE_SEGMENT_TYPE_T";
    }

    typedef  srte_segment_type_2_t {
        type enumeration {
            enum segment-type-2 {
                value 2;
                description "Segment-descriptor type: SRv6 Prefix";
            }
        }
        description "type definition for SRTE_SEGMENT_TYPE_2_T";
    }

    typedef  srte_policy_oper_state_t {
        type enumeration {
            enum up {
                value 1;
                description "SR policy is operationally up";
            }
            enum down {
                value 2;
                description "SR policy is operationally down";
            }
        }
        description "type definition for SRTE_POLICY_OPER_STATE_T";
    }

    typedef  srte_protocol_origin_type_type_t {
        type enumeration {
            enum pcep {
                value 10;
                description "PCEP used as signalling mechanism for the candidate path";
            }
            enum bgp {
                value 20;
                description "BGP used as signalling mechanism for the candidate path";
            }
            enum local {
                value 30;
                description "CLI, Yang model via Netconf, etc used for candidate path instantiation";
            }
        }
        description "type definition for SRTE_PROTOCOL_ORIGIN_TYPE_TYPE_T";
    }

    typedef  srte_explicite_null_type_t {
        type enumeration {
            enum ipv4 {
                value 1;
                description "IPV4 explicit label";
            }
        }
        description "type definition for SRTE_EXPLICITE_NULL_TYPE_T";
    }

    typedef  srte_ip_constraint_hop_type_t {
        type enumeration {
            enum loose {
                value 0;
                description "Make this constraint loose";
            }
            enum strict {
                value 1;
                description "Make this constraint strict";
            }
        }
        description "type definition for SRTE_IP_CONSTRAINT_HOP_TYPE_T";
    }

    typedef  srte_cp_metric_type_t {
        type enumeration {
            enum igp {
                value 1;
                description "IGP-Metric";
            }
            enum te {
                value 2;
                description "TE-Metric";
            }
        }
        description "type definition for SRTE_CP_METRIC_TYPE_T";
    }

    typedef  sr_te_debug_t {
        type bits {
            bit policy {
                position 0;
                description "Policy related information";
            }
            bit cp {
                position 1;
                description "Candidate-Path related information";
            }
            bit pce {
                position 2;
                description "PCE related information";
            }
        }
        description "type definition for SR_TE_DEBUG_T";
    }

    typedef  srv6_te_debug_t {
        type bits {
            bit policy {
                position 0;
                description "Policy related information";
            }
            bit cp {
                position 1;
                description "Candidate-Path related information";
            }
        }
        description "type definition for SRV6_TE_DEBUG_T";
    }

    typedef  sr_te_admin_group_type_t {
        type enumeration {
            enum exclude-any {
                value 1;
                description "exclude-any";
            }
            enum include-any {
                value 2;
                description "include-any";
            }
            enum include-all {
                value 3;
                description "include-all";
            }
        }
        description "type definition for SR_TE_ADMIN_GROUP_TYPE_T";
    }

    typedef  sr_policy_bsid_oper_state {
        type enumeration {
            enum pending {
                value 1;
                description "Oper-state Pending";
            }
            enum programmed {
                value 3;
                description "Oper-state Programmed";
            }
            enum conflict {
                value 4;
                description "Oper-state Conflict";
            }
        }
        description "type definition for SR_POLICY_BSID_OPER_STATE";
    }

    typedef  if_sr_prefix_flag_t {
        type enumeration {
            enum explicit-null {
                value 1;
                description "Set explicit-null";
            }
            enum no-php {
                value 2;
                description "Set no-PHP";
            }
        }
        description "datatype for segment routing prefix flag";
    }

    typedef  if_sr_n_flag_clear_t {
        type enumeration {
            enum n-flag-clear {
                value 1;
                description "Clear n-flag";
            }
        }
        description "datatype for segment routing N flag";
    }

}

/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-udld.yang
*
*/

module ipi-udld {

    yang-version 1.1;

    namespace   "http://www.ipinfusion.com/yang/ocnos/ipi-udld";

    prefix "ipi-udld";

    include ipi-udld-interface { revision-date 2021-10-25;}
    organization
        "IP Infusion Inc.";

    contact
        "Address: 3965 Freedom Circle, Suite 200, Santa Clara, CA 95054
         Phone: +1 408-400-1900
         E-mail: support@ipinfusion.com
         Web: http://www.ipinfusion.com/";

    description
        "Datamodel for Layer-2 UnDirectional Link Detection";


    revision "2021-10-25" {
        description "Restructured UDLD module in accordance with OpenConfig style";
        reference " 0.1.0.";
    }

    revision "2018-06-21" {
        description "Initial Version";
        reference "Initial Version";
    }

    grouping udld-global-config {
        description
            "Grouping for UDLD Global configuration data";
        leaf enable  {
            type  empty;
            description "Use this attribute to enable UDLD";
        } // END of enable definition.

        leaf message-time  {
            type  uint8 {
                 range "7..90"  {
                    description "7..90:Message interval step of 1 sec";
                 }
            }
            description "Use this attribute to set UDLD message interval value";
        } // END of message-time definition.

    } // END of udld-global-config definition.
    grouping udld-global-top {
        description
            "Grouping for UDLD Global";
        container global {
            description
                "Container for UDLD Global configuration";
            container config {
                description
                    "Configuration data for UDLD Global";
                uses udld-global-config;
            } // END of config-container definition.
            container state {
                config false;
                description
                    "Operational state data for UDLD Global";
                uses udld-global-config;
            } // END of state-container definition.
        } // END of global-container definition.
    } // END of udld-global-top definition.

    grouping  udld-grouping {
    description
        "UniDirectional Link Detection (UDLD) data model";
    container udld {
        description
            "UniDirectional Link Detection (UDLD) data model";
        uses udld-global-top;
        uses udld-interface-top;
    } // END of udld-container definition.
    } // END of udld-grouping definition.

    uses udld-grouping;

}

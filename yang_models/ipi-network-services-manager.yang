/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-network-services-manager.yang
*
*/

module ipi-network-services-manager {

    yang-version 1.1;

    namespace   "http://www.ipinfusion.com/yang/ocnos/ipi-network-services-manager";

    prefix "ipi-network-services-manager";

    import ipi-network-services-manager-types {
        prefix ipi-network-services-manager-types;
        revision-date 2021-09-03;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "This module provides user with the possibility of configuring debug
                options for Network Services Manager and Packet Manager";


    revision "2021-11-21" {
        description "Moved L2 depenedecies under HAVE_L2";
        reference "Initial Version";
    }

    revision "2021-09-03" {
        description "Update descriptions of attribute";
        reference "Initial Version";
    }

    revision "2021-07-30" {
        description "Initial Version";
        reference "Initial Version";
    }

    grouping net-serv-mgr-debug-term-pktmgr-state {
        description
            "netCMLSEPservCMLSEPmgrCMLSEPdebugCMLSEPtermCMLSEPpktmgrCMLSEPstate";
        leaf debug-options-pktmgr  {
            if-feature feature-list:HAVE_L2;
            type  ipi-network-services-manager-types:nsm_pkt_mgr_debug_type_t;
            description "Terminal debug for pkt-mgr debug";
        } // END of debug-options-pktmgr definition.

    } // END of net-serv-mgr-debug-term-pktmgr-state definition.
    grouping net-serv-mgr-debug-term-nsm-state {
        description
            "netCMLSEPservCMLSEPmgrCMLSEPdebugCMLSEPtermCMLSEPnsmCMLSEPstate";
        leaf debug-options-nsm  {
            type  ipi-network-services-manager-types:nsm_debug_type_t;
            description "Terminal debug for nsm debug";
        } // END of debug-options-nsm definition.

    } // END of net-serv-mgr-debug-term-nsm-state definition.
    grouping net-serv-mgr-debug-term-top {
        description
            "netCMLSEPservCMLSEPmgrCMLSEPdebugCMLSEPtermCMLSEPtop";
        container terminal {
            config false;
            description
                "Container for terminal debug";
            container nsm {
                config false;
                description
                    "Container for nsm terminal debug";
                container state {
                    config false;
                    description
                        "Operational state data";
                    uses net-serv-mgr-debug-term-nsm-state;
                } // END of state-container definition.
            } // END of nsm-container definition.
            container pkt-mgr {
                config false;
                description
                    "Container for pkt-mgr terminal debug";
                container state {
                    config false;
                    description
                        "Operational state data";
                    uses net-serv-mgr-debug-term-pktmgr-state;
                } // END of state-container definition.
            } // END of pkt-mgr-container definition.
        } // END of terminal-container definition.
    } // END of net-serv-mgr-debug-term-top definition.
    grouping net-serv-mgr-debug-pktmgr-config {
        description
            "netCMLSEPservCMLSEPmgrCMLSEPdebugCMLSEPpktmgrCMLSEPconfig";
        leaf debug-options  {
            if-feature feature-list:HAVE_L2;
            type  ipi-network-services-manager-types:nsm_pkt_mgr_debug_type_t;
            description "Use this attribute to debug vlan packet";
        } // END of debug-options definition.

    } // END of net-serv-mgr-debug-pktmgr-config definition.
    grouping net-serv-mgr-debug-pktmgr-top {
        description
            "netCMLSEPservCMLSEPmgrCMLSEPdebugCMLSEPpktmgrCMLSEPtop";
        container pkt-mgr {
            description
                "Container that holds pkt-mgr debug data";
            container config {
                description
                    "Configuration data for pkt-mgr debug data";
                uses net-serv-mgr-debug-pktmgr-config;
            } // END of config-container definition.
            container state {
                config false;
                description
                    "Operational state data for pkt-mgr debug data";
                uses net-serv-mgr-debug-pktmgr-config;
            } // END of state-container definition.
        } // END of pkt-mgr-container definition.
    } // END of net-serv-mgr-debug-pktmgr-top definition.
    grouping net-serv-mgr-debug-nsm-config {
        description
            "netCMLSEPservCMLSEPmgrCMLSEPdebugCMLSEPnsmCMLSEPconfig";
        leaf debug-options  {
            type  ipi-network-services-manager-types:nsm_debug_type_t;
            description "Use this attribute to debug nsm";
        } // END of debug-options definition.

    } // END of net-serv-mgr-debug-nsm-config definition.
    grouping net-serv-mgr-debug-nsm-top {
        description
            "netCMLSEPservCMLSEPmgrCMLSEPdebugCMLSEPnsmCMLSEPtop";
        container nsm {
            description
                "Container that holds nsm debug data";
            container config {
                description
                    "Configuration data for nsm debug data";
                uses net-serv-mgr-debug-nsm-config;
            } // END of config-container definition.
            container state {
                config false;
                description
                    "Operational state data for nsm debug data";
                uses net-serv-mgr-debug-nsm-config;
            } // END of state-container definition.
        } // END of nsm-container definition.
    } // END of net-serv-mgr-debug-nsm-top definition.
    grouping net-serv-mgr-debug-top {
        description
            "netCMLSEPservCMLSEPmgrCMLSEPdebugCMLSEPtop";
        container debug {
            description
                "Container that stores all debug data for network services manager";
            uses net-serv-mgr-debug-nsm-top;
            uses net-serv-mgr-debug-pktmgr-top;
            uses net-serv-mgr-debug-term-top;
        } // END of debug-container definition.
    } // END of net-serv-mgr-debug-top definition.

    grouping  network-services-manager-grouping {
    description
        "Container for all data related to network services manager";
    container network-services-manager {
        description
            "Container for all data related to network services manager";
        uses net-serv-mgr-debug-top;
    } // END of network-services-manager-container definition.
    } // END of network-services-manager-grouping definition.

    uses network-services-manager-grouping;

    rpc nsm-terminal-debug-on {
        description "Enable nsm terminal debug categories";
        input  {
            leaf debug-options  {
                type ipi-network-services-manager-types:nsm_exec_debug_type_t;
                mandatory true;
                description "Bitmap representing nsm debug categories";
            }
        }
    }

    rpc nsm-terminal-debug-off {
        description "Disable nsm terminal debug categories";
        input  {
            leaf debug-options  {
                type ipi-network-services-manager-types:nsm_exec_debug_type_t;
                mandatory true;
                description "Bitmap representing nsm debug categories";
            }
        }
    }

    rpc pktmgr-terminal-debug-on {
        description "Enable pktmgr terminal debug categories";
        input  {
            leaf debug-options  {
                type ipi-network-services-manager-types:nsm_pkt_mgr_debug_type_t;
                mandatory true;
                description "Bitmap representing pktmgr debug categories";
            }
        }
    }

    rpc pktmgr-terminal-debug-off {
        description "Disable pktmgr terminal debug categories";
    }

    rpc pktmgr-debug-statistics-enable {
        description "Used to enable pktmgr debug statistics";
    }

    rpc pktmgr-debug-statistics-disable {
        description "Used to disable pktmgr debug statistics";
    }

    rpc pktmgr-debug-statistics-get {
        description "Get pktmgr statistics from HW and put on log";
    }

    rpc pktmgr-debug-error-statistics-get {
        description "Get pktmgr debug error statistics and put on log";
        input  {
            leaf debug-error-statistics  {
                type ipi-network-services-manager-types:nsm_pktmgr_statistics_type_t;
                mandatory true;
                description "set exec mode debug commands error stats";
            }
        }
    }

    rpc clear-nsm-ipc-statistics {
        description "Use this RPC to clear statistics from nsm ipc";
    }

    rpc nsm-snmp-restart {
        description "Use this RPC to restart SNMP for nsm";
    }

}

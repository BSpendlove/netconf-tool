/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-vlan.yang
*
*/

module ipi-vlan {

    yang-version 1.1;

    namespace   "http://www.ipinfusion.com/yang/ocnos/ipi-vlan";

    prefix "ipi-vlan";

    import cml-data-types {
        prefix cml-data-types;
        revision-date 2022-04-04;
    }

    import ipi-vlan-types {
        prefix ipi-vlan-types;
        revision-date 2021-09-07;
    }

    import ipi-interface {
        prefix ipi-interface;
        revision-date 2022-04-05;
    }

    import ipi-network-instance {
        prefix ipi-network-instance;
        revision-date 2021-11-10;
    }

    import ipi-bridge {
        prefix ipi-bridge;
        revision-date 2022-01-13;
    }

    import ipi-qos {
        prefix ipi-qos;
        revision-date 2022-01-13;
    }

    import ietf-inet-types {
        prefix inet;
        revision-date 2013-07-15;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "VLAN configuration";


    revision "2022-01-18" {
        description "Remove yang-drop tag to show type parameter of customer-vlan list";
        reference " 0.6.3.";
    }

    revision "2021-11-23" {
        description "Netconf support for vlan-reservation CLI";
        reference " 0.6.2.";
    }

    revision "2021-11-16" {
        description "Added some if-feature to fix customer SKU compilation";
        reference " 0.6.1.";
    }

    revision "2021-10-18" {
        description "Removed custom DB triggers and added Netconf support for private VLAN feature";
        reference " 0.6.0.";
    }

    revision "2021-09-18" {
        description "Private VLAN DB clearance issues fixed";
        reference " 0.5.5.";
    }

    revision "2021-09-15" {
        description "Removing implicit-delete tags that were generated as warnings in zebm log";
        reference " 0.5.4.";
    }

    revision "2021-09-07" {
        description "Fix for JIRA-50146 - converted tagged-interface to leaf-list ";
        reference " 0.5.3.";
    }

    revision "2021-08-26" {
        description "Fix for JIRA-49703 pertaining to PB transactional CLIs";
        reference " 0.5.2.";
    }

    revision "2021-08-01" {
        description "Restructured current Provider Bridging hierarchy to OpenConfig style.";
        reference " 0.5.1.";
    }

    revision "2021-07-29" {
        description "Netconf support for port security feature enabled";
        reference " 0.5.0.";
    }

    revision "2021-04-08" {
        description "Data model chagnes done for ocmp-608";
        reference " 0.4.1.";
    }

    revision "2021-04-01" {
        description "Restructured current VLAN Classifier hierarchy to OpenConfig style.";
        reference " 0.4.0.";
    }

    revision "2021-03-30" {
        description "Cleared pyang lint reported warnings";
        reference " 0.3.1.";
    }

    revision "2021-01-27" {
        description "Change to have descriptions for individual leafs";
        reference " 0.3.0.";
    }

    revision "2020-12-15" {
        description "Change to have data-types in lower case instead of camel case";
        reference " 0.2.0.";
    }

    revision "2018-06-21" {
        description "Initial Version";
        reference " 0.1.0.";
    }

    grouping vlan-config {
        description
            "Grouping for vlan configuration data";
        leaf name  {
            type  string {
                length "1..32";
                pattern "[^?' =,>|]+";
            }
            description "Attribute to add or remove the name for a particular VLAN on the
                        bridge";
        } // END of name definition.

        leaf state  {
            type  ipi-vlan-types:vlan_state_t;
            description "Attribute to enable or disable the VLAN State on the bridge";
        } // END of state definition.

        leaf mtu  {
            if-feature feature-list:HAVE_SWFWDR;
            type  uint32;
            default "1500";
            description "Attribute to set the Maximum Transmission Unit (MTU) for a specified
                        VLAN. Any packet with a size greater than the configured MTU is
                        discarded";
        } // END of mtu definition.

    } // END of vlan-config definition.
    grouping vlan-common-config {
        description
            "Grouping for vlan common configuration data";
        leaf vlan-id  {
            type  cml-data-types:cml_range_t;
            description "Vlan identifier";
        } // END of vlan-id definition.

        leaf disable-mac-learning  {
            type  empty;
            description "Use attribute to disable mac address learning";
        } // END of disable-mac-learning definition.

    } // END of vlan-common-config definition.
    grouping vlan-state {
        description
            "Grouping for vlan operational data";
        leaf operational-status  {
            type  ipi-vlan-types:vlan_oper_status_t;
            description "Attribute specifies VLAN opertional status";
        } // END of operational-status definition.

        leaf-list tagged-interface  {
            type  string {
                length "1..1965";
                pattern "[^?' =,>|]+";
            }
            description "Vlan tagged interface";
        } // END of tagged-interface definition.

    } // END of vlan-state definition.
    grouping vlan-interface-config {
        description
            "Grouping for interface vlan mapping configuration data";
        leaf allow-vlan  {
            type  ipi-vlan-types:vlan_allowed_forbidden_t;
            default "forbidden";
            description "Attribute to spcecify vlan to be allowed or not";
        } // END of allow-vlan definition.

        leaf multicast  {
            type  boolean;
            default false;
            description "Attribute to spcecify vlan is multicast or not";
        } // END of multicast definition.

        leaf attach  {
            type  ipi-vlan-types:cml_add_remove_t;
            default "remove";
            description "Attribute to add or remove entry";
        } // END of attach definition.

    } // END of vlan-interface-config definition.
    grouping vlan-interface-top {
        description
            "Top level grouping for interface vlan mapping configuration and state
                        data";
    } // END of vlan-interface-top definition.
    grouping private-vlan-association-config {
        description
            "Grouping for private vlan association configuration and state data";
        leaf secondary-vlan  {
            type  cml-data-types:cml_range_t;
            description "Use this attribute to configure associated secondary vlan for private
                        vlan";
        } // END of secondary-vlan definition.

    } // END of private-vlan-association-config definition.
    grouping private-vlan-association-top {
        description
            "Top level grouping for private vlan association configuration and
                        state data";
        container association {
            when " ../config/type ";
            description
                "Seconddry vlans associated with primary private vlans";
            container config {
                description
                    "Configuration data for private vlan association";
                uses private-vlan-association-config;
            } // END of config-container definition.
            container state {
                config false;
                description
                    "Operational state data";
                uses private-vlan-association-config;
            } // END of state-container definition.
        } // END of association-container definition.
    } // END of private-vlan-association-top definition.
    grouping private-vlan-config {
        description
            "Grouping for private vlan configuration data";
        leaf type  {
            type  ipi-vlan-types:vlan_pvlan_type_t;
            mandatory true;
            description "private vlan type";
        } // END of type definition.

    } // END of private-vlan-config definition.
    grouping private-vlan-top {
        description
            "Top level grouping for private vlan configuration and state data";
        container private-vlan {
            when " /ipi-network-instance:network-instances/ipi-network-instance:network-instance/ipi-bridge:bridge/ipi-bridge:config/ipi-bridge:protocol = 'ieee vlan-bridge' or /ipi-network-instance:network-instances/ipi-network-instance:network-instance/ipi-bridge:bridge/ipi-bridge:config/ipi-bridge:protocol = 'rstp vlan-bridge' or /ipi-network-instance:network-instances/ipi-network-instance:network-instance/ipi-bridge:bridge/ipi-bridge:config/ipi-bridge:protocol = 'mstp' or /ipi-network-instance:network-instances/ipi-network-instance:network-instance/ipi-bridge:bridge/ipi-bridge:config/ipi-bridge:protocol = 'mstp ring' ";
            if-feature feature-list:HAVE_PVLAN;
            description
                "List of priate vlans";
            container config {
                presence "Configure private vlan type";
                description
                    "Configuration data of private vlans";
                uses private-vlan-config;
            } // END of config-container definition.
            container state {
                config false;
                description
                    "Operational state data";
                uses private-vlan-config;
            } // END of state-container definition.
            uses private-vlan-association-top;
        } // END of private-vlan-container definition.
    } // END of private-vlan-top definition.
    grouping cvlan-type-config {
        description
            "Grouping for customer VLAN configuration data";
        leaf type  {
            type  ipi-vlan-types:cvlan_type_t;
            description "Attribute to configure type for a particular VLAN on the bridge";
        } // END of type definition.

    } // END of cvlan-type-config definition.
    grouping customer-vlan-top {
        description
            "Top level grouping for customer VLAN data";
        container customer-vlan {
            when " /ipi-network-instance:network-instances/ipi-network-instance:network-instance/ipi-bridge:bridge/ipi-vlan:vlans/ipi-vlan:vlan/ipi-vlan:customer-vlan/ipi-vlan:config/ipi-vlan:type ";
            description
                "Container for customer VLAN configuration and state data";
            container config {
                description
                    "Customer VLAN configuration data";
                uses cvlan-type-config;
                uses vlan-config;
            } // END of config-container definition.
            container state {
                config false;
                description
                    "Customer VLAN operational state data";
                uses cvlan-type-config;
                uses vlan-config;
                uses vlan-state;
            } // END of state-container definition.
        } // END of customer-vlan-container definition.
    } // END of customer-vlan-top definition.
    grouping svlan-type-config {
        description
            "Grouping for service vlan configuration data";
        leaf type  {
            type  ipi-vlan-types:svlan_type_t;
            mandatory true;
            description "Attribute to configure type for a particular VLAN on the bridge";
        } // END of type definition.

    } // END of svlan-type-config definition.
    grouping service-vlan-top {
        description
            "Top level grouping for service vlan configuration and state data";
        container service-vlan {
            if-feature feature-list:HAVE_PROVIDER_BRIDGE;
            description
                "Container for service vlans";
            container config {
                description
                    "Configuration data for service vlan";
                uses svlan-type-config;
                uses vlan-config;
            } // END of config-container definition.
            container state {
                config false;
                description
                    "Operational state data";
                uses svlan-type-config;
                uses vlan-config;
                uses vlan-state;
            } // END of state-container definition.
        } // END of service-vlan-container definition.
    } // END of service-vlan-top definition.
    grouping vlan-top {
        description
            "Top level grouping for vlan configuration and state data";

        list vlan {
        when " /ipi-network-instance:network-instances/ipi-network-instance:network-instance/ipi-bridge:bridge/ipi-vlan:vlans/ipi-vlan:vlan/ipi-vlan:customer-vlan/ipi-vlan:config/ipi-vlan:type  or /ipi-network-instance:network-instances/ipi-network-instance:network-instance/ipi-bridge:bridge/ipi-vlan:vlans/ipi-vlan:vlan/ipi-vlan:service-vlan/ipi-vlan:config/ipi-vlan:type ";
            key "vlan-id";
            description
                "List for vlan configuration and state data";
            leaf vlan-id  {
                type  leafref {
                    path  "../config/vlan-id";
                }
                description "Vlan identifier";
            } // END of vlan-id definition.

            container config {
                description
                    "Configuration data for vlan";
                uses vlan-common-config;
            } // END of config-container definition.
            container state {
                config false;
                description
                    "Operational state data";
                uses vlan-common-config;
            } // END of state-container definition.
            uses customer-vlan-top;
            uses service-vlan-top;
            uses vlan-interface-top;
            uses private-vlan-top;
        } // End of vlan-list
    } // END of vlan-top definition.
    grouping rule-criteria-config {
        description
            "Grouping for VLAN classifier rule criteria configuration";
        leaf mac-address  {
            type  cml-data-types:cml_mac_addr_t {
                length "1..1965";
            }
            description "Use this attribute to configure classifier for given MAC address";
        } // END of mac-address definition.

        leaf ipv4-address  {
            type  inet:ipv4-prefix;
            description "Use this attribute to configure classifier for given IPv4 address";
        } // END of ipv4-address definition.

        leaf ether-type  {
            type  ipi-vlan-types:vlan_classifier_ethertype_t;
            description "Use this attribute to configure classifier for protocols based on
                        Ethertype value";
        } // END of ether-type definition.

    } // END of rule-criteria-config definition.
    grouping rule-criteria-top {
        description
            "Top level grouping for VLAN classifier rule criteria data";
        container rule-criteria {
            description
                "List for VLAN classifier rule criterias configuration and state data";
            container config {
                description
                    "Configuration data for classifier rule criteria";
                uses rule-criteria-config;
            } // END of config-container definition.
            container state {
                config false;
                description
                    "Operational state data for classifier rule criteria";
                uses rule-criteria-config;
            } // END of state-container definition.
        } // END of rule-criteria-container definition.
    } // END of rule-criteria-top definition.
    grouping rule-config {
        description
            "Grouping for VLAN classifier rule configuration";
        leaf rule-id  {
            type  uint16 {
                 range "1..256"  {
                    description "1..256:VLAN classifier rule ID";
                 }
            }
            description "Classifier rule ID";
        } // END of rule-id definition.

    } // END of rule-config definition.
    grouping rule-top {
        description
            "Top level grouping for VLAN classifier rule data";

        list classifier-rule {
        when " /ipi-vlan:vlan-classifier/ipi-vlan:classifier-rule/ipi-vlan:rule-criteria/ipi-vlan:config/ipi-vlan:mac-address  or /ipi-vlan:vlan-classifier/ipi-vlan:classifier-rule/ipi-vlan:rule-criteria/ipi-vlan:config/ipi-vlan:ipv4-address  or /ipi-vlan:vlan-classifier/ipi-vlan:classifier-rule/ipi-vlan:rule-criteria/ipi-vlan:config/ipi-vlan:ether-type ";
            key "rule-id";
            description
                "List for VLAN classifier rule configuration and state data";
            leaf rule-id  {
                type  leafref {
                    path  "../config/rule-id";
                }
                description "Classifier rule id";
            } // END of rule-id definition.

            container config {
                description
                    "Configuration data for classifier rule";
                uses rule-config;
            } // END of config-container definition.
            container state {
                config false;
                description
                    "Operational state data for classifier rule";
                uses rule-config;
            } // END of state-container definition.
            uses rule-criteria-top;
        } // End of classifier-rule-list
    } // END of rule-top definition.
    grouping group-config {
        description
            "Grouping for classifier group configuration";
        leaf group-id  {
            type  uint8 {
                 range "1..16"  {
                    description "1..16:VLAN classifier group ID";
                 }
            }
            description "VLAN classifier group ID";
        } // END of group-id definition.

        leaf rule-id  {
            type  leafref {
                path  "/vlan-classifier/classifier-rule/rule-id";
            }
            description "VLAN classifier rule ID";
        } // END of rule-id definition.

    } // END of group-config definition.
    grouping group-top {
        description
            "Top level grouping for VLAN classifier group data";

        list classifier-group {
            key "group-id rule-id";
            description
                "List for VLAN classifier group configuration and state data";
            leaf group-id  {
                type  leafref {
                    path  "../config/group-id";
                }
                description "Classifier group ID";
            } // END of group-id definition.

            leaf rule-id  {
                type  leafref {
                    path  "../config/rule-id";
                }
                description "Classifier rule ID";
            } // END of rule-id definition.

            container config {
                description
                    "Configuration data for VLAN classifier group";
                uses group-config;
            } // END of config-container definition.
            container state {
                config false;
                description
                    "Operational state data for VLAN classifier group";
                uses group-config;
            } // END of state-container definition.
        } // End of classifier-group-list
    } // END of group-top definition.
    grouping port-config {
        description
            "Grouping for classifier port configuration";
        leaf port-name  {
            type  leafref {
                path  "/ipi-interface:interfaces/ipi-interface:interface/ipi-interface:name";
            }
            description "Port mapped with VLAN classifier";
        } // END of port-name definition.

        leaf group-id  {
            type  leafref {
                path  "/vlan-classifier/classifier-group/group-id";
            }
            description "VLAN classifier group ID";
        } // END of group-id definition.

        leaf vlan-id  {
            type  leafref {
                path  "/ipi-network-instance:network-instances/ipi-network-instance:network-instance/ipi-bridge:bridge/vlans/vlan/vlan-id";
            }
            mandatory true;
            description "Use this attribute to map VLAN ID with classifier group";
        } // END of vlan-id definition.

    } // END of port-config definition.
    grouping port-top {
        description
            "Top level grouping for port VLAN classifier data";

        list port {
        when " /ipi-vlan:vlan-classifier/ipi-vlan:port/ipi-vlan:config/ipi-vlan:vlan-id + /ipi-network-instance:network-instances/ipi-network-instance:network-instance/ipi-bridge:bridge/ipi-bridge:bridge-ports/ipi-bridge:interface/ipi-bridge:config/ipi-bridge:name ";
            key "port-name group-id";
            description
                "List for port mapping with VLAN classifier configuration and state
                            data";
            leaf port-name  {
                type  leafref {
                    path  "../config/port-name";
                }
                description "Port mapped with VLAN classifier";
            } // END of port-name definition.

            leaf group-id  {
                type  leafref {
                    path  "../config/group-id";
                }
                description "VLAN classifier group ID";
            } // END of group-id definition.

            container config {
                description
                    "Configuration data for port VLAN classifier";
                uses port-config;
            } // END of config-container definition.
            container state {
                config false;
                description
                    "Operational state data for port VLAN classifier";
                uses port-config;
            } // END of state-container definition.
        } // End of port-list
    } // END of port-top definition.
    grouping reserve-vlan-config {
        description
            "Grouping for reserve vlan configuration data";
        leaf vlan-id  {
            type  cml-data-types:cml_range_t;
            description "Use attribute to reserve vlan";
        } // END of vlan-id definition.

    } // END of reserve-vlan-config definition.
    grouping reserve-vlan-top {
        description
            "Top level grouping for reserve vlan configuration and state data";

        list reserve-vlan {
            if-feature feature-list:HAVE_FLEXPORT;
            key "vlan-id";
            description
                "List for reserve vlan configuration and state data";
            leaf vlan-id  {
                type  leafref {
                    path  "../config/vlan-id";
                }
                description "Vlan identifier";
            } // END of vlan-id definition.

            container config {
                description
                    "Configuration data of reserve vlans";
                uses reserve-vlan-config;
            } // END of config-container definition.
            container state {
                config false;
                description
                    "Operational state data";
                uses reserve-vlan-config;
            } // END of state-container definition.
        } // End of reserve-vlan-list
    } // END of reserve-vlan-top definition.
    grouping ovc-oep-config {
        description
            "Grouping for OEP configuration";
        leaf id  {
            type  string {
                length "1..1965";
                pattern "[^?' =,>|]+";
            }
            description "Operator Virtual Connection identifier";
        } // END of id definition.

        leaf oep-id  {
            type  string {
                length "1..1965";
                pattern "[^?' =,>|]+";
            }
            description "OVC end point identifier";
        } // END of oep-id definition.

    } // END of ovc-oep-config definition.
    grouping oep-config-top {
        description
            "Top level grouping for OVC configuration";

        list oep {
            key "id";
            description
                "List for ovc end point configuration and state data";
            leaf id  {
                type  leafref {
                    path  "../config/id";
                }
                description "Operator Virtual Connection identifier";
            } // END of id definition.

            container config {
                description
                    "Configuration data for OEP";
                uses ovc-oep-config;
            } // END of config-container definition.
            container state {
                config false;
                description
                    "Operational state data";
                uses ovc-oep-config;
            } // END of state-container definition.
        } // End of oep-list
    } // END of oep-config-top definition.
    grouping ovc-config {
        description
            "Grouping for OVC configuration";
        leaf svlan-id  {
            type  uint16 {
                 range "2..4094"  {
                    description "2..4094:S-VLAN ID";
                 }
            }
            description "Servivce vlan identifier";
        } // END of svlan-id definition.

        leaf evc-id  {
            type  string {
                length "1..1965";
                pattern "[^?' =,>|]+";
            }
            description "Ethernet Virtual Connection identifier";
        } // END of evc-id definition.

        leaf maximum-uni-number  {
            type  uint32 {
                 range "1..32"  {
                    description "1..32:enter the number of max uni for the EVC/SVLAN";
                 }
            }
            description "Specifies maximum mumber of UNIs for the given EVC/SVLAN";
        } // END of maximum-uni-number definition.

    } // END of ovc-config definition.
    grouping ovc-preserve-config {
        description
            "Grouping for OVC preserve configuration";
        leaf ovc-id  {
            when " /ipi-network-instance:network-instances/ipi-network-instance:network-instance/ipi-bridge:bridge/ipi-vlan:operator-virtual-connection/ipi-vlan:config/ipi-vlan:svlan-id ";
            type  string {
                length "1..1965";
                pattern "[^?' =,>|]+";
            }
            description "Operator Virtual Connection identifier";
        } // END of ovc-id definition.

        leaf type  {
            type  ipi-vlan-types:vlan_ce_svlan_t;
            description "Customer or service vlan type";
        } // END of type definition.

        leaf preserve  {
            type  ipi-vlan-types:vlan_preserve_type_t;
            description "Attribute to configure cos or vlan id preservation";
        } // END of preserve definition.

    } // END of ovc-preserve-config definition.
    grouping oep-vlan-config {
        description
            "Grouping for OVC end point mapping vlan configuration";
        leaf oep-vlan-id  {
            type  uint16;
            description "OEP mapping vlan id";
        } // END of oep-vlan-id definition.

        leaf type  {
            type  ipi-vlan-types:vlan_oepvlan_type_t;
            description "OEP mapping vlan type";
        } // END of type definition.

        leaf oep-id  {
            type  string {
                length "1..1965";
                pattern "[^?' =,>|]+";
            }
            mandatory true;
            description "OVC end point identifier";
        } // END of oep-id definition.

    } // END of oep-vlan-config definition.
    grouping oep-vlan-top {
        description
            "Top level grouping for OVC end point mapping vlan configuration";

        list vlan {
            key "type oep-vlan-id";
            description
                "List for oep vlans";
            leaf type  {
                type  leafref {
                    path  "../config/type";
                }
                description "OEP mapping vlan type";
            } // END of type definition.

            leaf oep-vlan-id  {
                type  leafref {
                    path  "../config/oep-vlan-id";
                }
                description "OEP mapping vlan id";
            } // END of oep-vlan-id definition.

            container config {
                description
                    "Configuration data for oep vlan";
                uses oep-vlan-config;
            } // END of config-container definition.
            container state {
                config false;
                description
                    "Operational state data";
                uses oep-vlan-config;
            } // END of state-container definition.
        } // End of vlan-list
    } // END of oep-vlan-top definition.
    grouping oep-config {
        description
            "Grouping for OVC end point mapping configuration";
        leaf oep-name  {
            type  string {
                length "1..1965";
                pattern "[^?' =,>|]+";
            }
            description "OVC end-point mapping name";
        } // END of oep-name definition.

    } // END of oep-config definition.
    grouping access-group-config {
        description
            "Grouping for access group matching configuration data";
        leaf group-name  {
            type  string {
                length "1..1965";
                pattern "[^?' =,>|]+";
            }
            description "Attribute specifies access list name to set actions by action-type";
        } // END of group-name definition.

        leaf acl-type  {
            type  ipi-vlan-types:vlan_acltype_t;
            description "Attribute to associate access-list to vlan access-map name";
        } // END of acl-type definition.

    } // END of access-group-config definition.
    grouping access-group-top {
        description
            "Top level group for access group data";

        list access-group {
            key "group-name acl-type";
            description
                "List for access group configuration and state data";
            leaf group-name  {
                type  leafref {
                    path  "../config/group-name";
                }
                description "Attribute specifies access list name to set match criteria";
            } // END of group-name definition.

            leaf acl-type  {
                type  leafref {
                    path  "../config/acl-type";
                }
                description "Attribute to associate access-list to vlan access-map name";
            } // END of acl-type definition.

            container config {
                description
                    "Configuration data for access group";
                uses access-group-config;
            } // END of config-container definition.
            container state {
                config false;
                description
                    "Operational state data";
                uses access-group-config;
            } // END of state-container definition.
        } // End of access-group-list
    } // END of access-group-top definition.
    grouping access-group-interface-config {
        description
            "Grouping access group port data";
        leaf action  {
            type  ipi-vlan-types:vlan_actiontype_t;
            description "Attribute to perform action on ingress traffic";
        } // END of action definition.

    } // END of access-group-interface-config definition.
    grouping access-group-interface-top {
        description
            "Top level grouping for access group port data";

        list interface {
            key "interface-name action";
            description
                "List for access group ports data";
            leaf interface-name  {
                type  leafref {
                    path  "/ipi-interface:interfaces/ipi-interface:interface/ipi-interface:name";
                }
                description "The textual name of the interface";
            } // END of interface-name definition.

            leaf action  {
                type  leafref {
                    path  "../config/action";
                }
                description "Attribute to perform action on ingress traffic";
            } // END of action definition.

            container config {
                description
                    "Configuration data for acess group intrface";
                uses access-group-interface-config;
            } // END of config-container definition.
            container state {
                config false;
                description
                    "Operational state data";
                uses access-group-interface-config;
            } // END of state-container definition.
        } // End of interface-list
    } // END of access-group-interface-top definition.
    grouping access-vlan-group {
        description
            "Grouping access vlan statistics data";
        leaf enable-statistics  {
            type  empty;
            description "Attribute to associate statistic per-entry to vlan access-map name";
        } // END of enable-statistics definition.

    } // END of access-vlan-group definition.
    grouping access-vlan-mapping-config {
        description
            "Grouping for access vlan mapping configuration data";
        leaf mapping-name  {
            type  string {
                length "1..1965";
                pattern "([1-9]|[12][0-9]|3[0-2])";
            }
            description "Attribute to create, update or delete a vlan access-map with default
                        sequenceID i.e. 10. There can be only one VLAN access-map with default
                        sequenceID";
        } // END of mapping-name definition.

        leaf filter-vlan-id  {
            type  cml-data-types:cml_range_t;
            description "Vlan filter name";
        } // END of filter-vlan-id definition.

    } // END of access-vlan-mapping-config definition.
    grouping access-vlan-mapping-top {
        description
            "Top level grouping for access vlan mapping configuration and state
                        data";

        list mapping {
            if-feature feature-list:HAVE_ACL;
            if-feature feature-list:HAVE_VLAN_ACCESS_MAP;
            key "mapping-name";
            description
                "List for access vlan mapping configuration and state data";
            leaf mapping-name  {
                type  leafref {
                    path  "../config/mapping-name";
                }
                description "Attribute to create, update or delete a vlan access-map with default
                            sequenceID i.e. 10. There can be only one VLAN access-map with default
                            sequenceID";
            } // END of mapping-name definition.

            container config {
                description
                    "Configuration data for access group mapping";
                uses access-vlan-group;
                uses access-vlan-mapping-config;
            } // END of config-container definition.
            container state {
                config false;
                description
                    "Operational state data";
                uses access-vlan-group;
                uses access-vlan-mapping-config;
            } // END of state-container definition.
            uses access-group-top;
            uses access-group-interface-top;
        } // End of mapping-list
    } // END of access-vlan-mapping-top definition.
    grouping access-vlan-mapping-sequence-config {
        description
            "Grouping access vlan sequence mapping data";
        leaf mapping-name  {
            type  string {
                length "1..1965";
                pattern "([1-9]|[12][0-9]|3[0-2])";
            }
            description "Attribute to create, update or delete a vlan access-map with default
                        sequenceID i.e. 10. There can be only one VLAN access-map with default
                        sequenceID";
        } // END of mapping-name definition.

        leaf sequence-number  {
            type  uint32 {
                 range "1..4294967295"  {
                    description "1..4294967295:Enter sequence number";
                 }
            }
            description "Attribute to create, update or deletes a vlan access-map with
                        sequenceID. There can be multiple one VLAN access-map with sequenceID
                        combination possible";
        } // END of sequence-number definition.

    } // END of access-vlan-mapping-sequence-config definition.
    grouping access-vlan-mapping-sequence-top {
        description
            "Top level grouping access vlan sequence mapping data";

        list mapping-sequence {
            if-feature feature-list:HAVE_ACL;
            if-feature feature-list:HAVE_VLAN_ACCESS_MAP;
            key "mapping-name sequence-number";
            description
                "List for access sequence mapping";
            leaf mapping-name  {
                type  leafref {
                    path  "../config/mapping-name";
                }
                description "Attribute to create, update or delete a vlan access-map with default
                            sequenceID i.e. 10. There can be only one VLAN access-map with default
                            sequenceID";
            } // END of mapping-name definition.

            leaf sequence-number  {
                type  leafref {
                    path  "../config/sequence-number";
                }
                description "Attribute to create, update or deletes a vlan access-map with
                            sequenceID. There can be multiple one VLAN access-map with sequenceID
                            combination possible";
            } // END of sequence-number definition.

            container config {
                description
                    "Configuration data for access sequence mapping";
                uses access-vlan-group;
                uses access-vlan-mapping-sequence-config;
            } // END of config-container definition.
            container state {
                config false;
                description
                    "Operational state data";
                uses access-vlan-group;
                uses access-vlan-mapping-sequence-config;
            } // END of state-container definition.
            uses access-group-top;
            uses access-group-interface-top;
        } // End of mapping-sequence-list
    } // END of access-vlan-mapping-sequence-top definition.
    grouping access-vlan-top {
        description
            "Top level grouping for access VLAN configuration data";
    } // END of access-vlan-top definition.
    grouping layer2-global-config {
        description
            "Grouping for Layer-2 Global Configuration data";
        leaf disable-vlan-classifier-feature  {
            if-feature feature-list:HAVE_VLAN_CLASS;
            type  empty;
            description "Use this command to enable or disable VLAN classifier feature.";
        } // END of disable-vlan-classifier-feature definition.

        leaf disable-port-security  {
            type  empty;
            description "Use this attribute to disable or enable port-security globally.";
        } // END of disable-port-security definition.

    } // END of layer2-global-config definition.
    grouping cvlan-registration-tables-top {
        description
            "Top level grouping for CVLAN registration entries's data";

        list cvlan-registration-table {
            key "table-name";
            description
                "CVLAN registration table that will have the mapping between CVLANs and
                            SVLANs";
            leaf table-name  {
                type  leafref {
                    path  "../config/table-name";
                }
                description "Use this to configure the name of the CVLAN registration table.";
            } // END of table-name definition.

            container config {
                description
                    "Configuration data for CVLAN registration table name";
                uses cvlan-registration-entry-config;
            } // END of config-container definition.
            container state {
                config false;
                description
                    "Operational state data for CVLAN registration table name";
                uses cvlan-registration-entry-config;
            } // END of state-container definition.
            uses cvlan-svlan-config-top;
        } // End of cvlan-registration-table-list
    } // END of cvlan-registration-tables-top definition.
    grouping cvlan-svlan-config-top {
        description
            "Grouping for CVLAN registration table's VLAN configuration";
        container cvlan-mappings {
            description
                "Enclosing container for the list for CVLAN registration table's VLAN
                        data";

            list cvlan-mapping {
            when " /ipi-network-instance:network-instances/ipi-network-instance:network-instance/ipi-bridge:bridge/ipi-vlan:vlans/ipi-vlan:vlan/ipi-vlan:config/ipi-vlan:vlan-id + /ipi-network-instance:network-instances/ipi-network-instance:network-instance/ipi-bridge:bridge/ipi-vlan:vlans/ipi-vlan:vlan/ipi-vlan:service-vlan/ipi-vlan:config/ipi-vlan:type + /ipi-network-instance:network-instances/ipi-network-instance:network-instance/ipi-bridge:bridge/ipi-vlan:vlans/ipi-vlan:vlan/ipi-vlan:config/ipi-vlan:vlan-id + /ipi-network-instance:network-instances/ipi-network-instance:network-instance/ipi-bridge:bridge/ipi-vlan:vlans/ipi-vlan:vlan/ipi-vlan:customer-vlan ";
                key "svlan-id cvlan-id";
                description
                    "List for CVLAN registration table's VLAN data";
                leaf svlan-id  {
                    type  leafref {
                        path  "../config/svlan-id";
                    }
                    description "Service VLAN ID in registration table";
                } // END of svlan-id definition.

                leaf cvlan-id  {
                    type  leafref {
                        path  "../config/cvlan-id";
                    }
                    description "Customer VLAN ID in registration table";
                } // END of cvlan-id definition.

                container config {
                    description
                        "Configuration data for CVLAN registration table entries";
                    uses cvlan-registration-entries-config;
                } // END of config-container definition.
                container state {
                    config false;
                    description
                        "Operational state data for CVLAN registration table entries";
                    uses cvlan-registration-entries-config;
                } // END of state-container definition.
            } // End of cvlan-mapping-list
        } // END of cvlan-mappings-container definition.
    } // END of cvlan-svlan-config-top definition.
    grouping cvlan-registration-entries-config {
        description
            "Grouping for CVLAN registration table name configuration";
        leaf svlan-id  {
            type  uint16 {
                 range "1..4095"  {
                    description "1..4095:SVLAN ID";
                 }
            }
            description "Service VLAN ID in registration table";
        } // END of svlan-id definition.

        leaf cvlan-id  {
            type  cml-data-types:cml_range_t;
            description "Customer VLAN ID in registration table";
        } // END of cvlan-id definition.

        leaf untagged-ep  {
            type  ipi-vlan-types:cvlan_config_t;
            description "Customer/provider edge port is untagged for specified CVLAN";
        } // END of untagged-ep definition.

        leaf translated-cvlan-id  {
            type  uint16 {
                 range "1..4095"  {
                    description "1..4095:Translated CVID";
                 }
            }
            description "Translated customer VLAN ID";
        } // END of translated-cvlan-id definition.

        leaf svlan-cos  {
            if-feature feature-list:NOT_HAVE_CUSTOM2_QOS;
            type  uint8 {
                 range "0..7"  {
                    description "0..7:Specify COS value 0-7";
                 }
            }
            description "Class of Service in the Priority Code Point (PCP) field of the Service
                        Provider Tag (STAG)";
        } // END of svlan-cos definition.

        leaf svlan-cfi  {
            if-feature feature-list:NOT_HAVE_CUSTOM2_QOS;
            type  uint8 {
                 range "0..1"  {
                    description "0..1:Specify CFI value 0-1";
                 }
            }
            description "Canonical Format Indicator in the Drop Eligible Indicator (DEI) field
                        of the STAG";
        } // END of svlan-cfi definition.

        leaf cvlan-cos  {
            if-feature feature-list:NOT_HAVE_CUSTOM2_QOS;
            type  uint8 {
                 range "0..7"  {
                    description "0..7:Specify COS value 0-7";
                 }
            }
            description "Class of Service in the PCP field of the customer tag (CTAG)";
        } // END of cvlan-cos definition.

        leaf cvlan-cfi  {
            if-feature feature-list:NOT_HAVE_CUSTOM2_QOS;
            type  uint8 {
                 range "0..1"  {
                    description "0..1:Specify CFI value 0-1";
                 }
            }
            description "Canonical Format Indicator in the DEI field of the CTAG";
        } // END of cvlan-cfi definition.

        leaf cos-to-queue  {
            if-feature feature-list:HAVE_CUSTOM2_QOS;
            type  leafref {
                path  "/ipi-qos:qos/ipi-qos:global/ipi-qos:map-profile/ipi-qos:cos-to-queue-profiles/ipi-qos:cos-to-queue-profile/ipi-qos:name";
            }
            description "Name of CoS to queue profile to map to CVLAN ID";
        } // END of cos-to-queue definition.

        leaf remark-cos  {
            when " /ipi-qos:qos/ipi-qos:global/ipi-qos:config/ipi-qos:enable-qos ";
            if-feature feature-list:HAVE_CUSTOM2_QOS;
            if-feature feature-list:HAVE_QOS;
            type  empty;
            description "Remark Egress Class of Service(COS)";
        } // END of remark-cos definition.

    } // END of cvlan-registration-entries-config definition.
    grouping cvlan-registration-entry-config {
        description
            "Grouping for CVLAN registration table name configuration";
        leaf table-name  {
            type  string {
                length "1..1965";
                pattern "[^?' =,>|]+";
            }
            description "Use this to configure the name of the CVLAN registration table.";
        } // END of table-name definition.

    } // END of cvlan-registration-entry-config definition.

    grouping  vlans-grouping {
    description
        "Top level container for vlan configuration and state data";
    container vlans {
        description
            "Top level container for vlan configuration and state data";
        uses vlan-top;
    } // END of vlans-container definition.
    } // END of vlans-grouping definition.

    grouping  vlan-classifier-grouping {
    description
        "Top level container for VLAN classifier configuration and state data";
    container vlan-classifier {
        when " not(/ipi-vlan:layer2-global/ipi-vlan:config/ipi-vlan:disable-vlan-classifier-feature) ";
        if-feature feature-list:HAVE_VLAN_CLASS;
        description
            "Top level container for VLAN classifier configuration and state data";
        uses rule-top;
        uses group-top;
        uses port-top;
    } // END of vlan-classifier-container definition.
    } // END of vlan-classifier-grouping definition.

    grouping  vlan-reservation-grouping {
    description
        "Top level container for VLAN reservation configuration and state data";
    container vlan-reservation {
        if-feature feature-list:HAVE_FLEXPORT;
        description
            "Top level container for VLAN reservation configuration and state data";
        uses reserve-vlan-top;
    } // END of vlan-reservation-container definition.
    } // END of vlan-reservation-grouping definition.

    grouping  layer2-global-grouping {
    description
        "Top level container for Layer2 global configuration and state data";
    container layer2-global {
        description
            "Top level container for Layer2 global configuration and state data";
        container config {
            description
                "Layer-2 global configuration data";
            uses layer2-global-config;
        } // END of config-container definition.
        container state {
            config false;
            description
                "Layer-2 global operational state data";
            uses layer2-global-config;
        } // END of state-container definition.
        uses access-vlan-top;
    } // END of layer2-global-container definition.
    } // END of layer2-global-grouping definition.

    grouping  cvlan-registration-tables-grouping {
    description
        "Top level container for CVLAN registration table configuration and
                state data";
    container cvlan-registration-tables {
        if-feature feature-list:HAVE_VLAN;
        if-feature feature-list:HAVE_PROVIDER_BRIDGE;
        description
            "Top level container for CVLAN registration table configuration and
                    state data";
        uses cvlan-registration-tables-top;
    } // END of cvlan-registration-tables-container definition.
    } // END of cvlan-registration-tables-grouping definition.

    augment /ipi-network-instance:network-instances/ipi-network-instance:network-instance/ipi-bridge:bridge {
        description
            "Top level container for vlan configuration and state data";
        uses vlans-grouping;
    }

    uses vlan-classifier-grouping;
    uses vlan-reservation-grouping;
    uses layer2-global-grouping;
    augment /ipi-network-instance:network-instances/ipi-network-instance:network-instance/ipi-bridge:bridge {
        description
            "Top level container for CVLAN registration table configuration and
                    state data";
        uses cvlan-registration-tables-grouping;
    }


}

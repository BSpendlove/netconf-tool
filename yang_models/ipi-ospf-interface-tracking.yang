/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ospf-interface-tracking.yang
*
*/

module ipi-ospf-interface-tracking {

    yang-version 1.1;

    namespace   "http://www.ipinfusion.com/yang/ocnos/ipi-ospf-interface-tracking";

    prefix "ipi-ospf-interface-tracking";

    import ietf-inet-types {
        prefix inet;
        revision-date 2013-07-15;
    }

    import ipi-interface {
        prefix ipi-interface;
        revision-date 2022-04-05;
    }

    import ipi-ospf-interface-tracking-types {
        prefix ipi-ospf-interface-tracking-types;
        revision-date 2021-11-16;
    }

    organization
        "IP Infusion Inc.";

    contact
        "Address: 3965 Freedom Circle, Suite 200, Santa Clara, CA 95054
         Phone: +1 408-400-1900
         E-mail: support@ipinfusion.com
         Web: http://www.ipinfusion.com/";

    description
        "This module provides OSPF interface tracking configuration";


    revision "2021-11-16" {
        description "Module restructuring";
        reference " 0.2.0.";
    }

    revision "2018-06-21" {
        description "Initial Version";
        reference " 0.1.0.";
    }

    grouping ospf-intf-event-tracking-actions-config {
        description
            "OSPF interface tracking actions configuration";
        leaf name  {
            type  leafref {
                path  "/ipi-interface:interfaces/ipi-interface:interface/ipi-interface:name";
            }
            description "Attribute used to specify the interface name for OSPF interface
                        tracking event action.";
        } // END of name definition.

        leaf cost  {
            type  uint32 {
                 range "1..65535"  {
                    description "1..65535:cost";
                 }
            }
            mandatory true;
            description "Attribute used to specify the interface cost for OSPF interface
                        tracking event action.";
        } // END of cost definition.

    } // END of ospf-intf-event-tracking-actions-config definition.
    grouping ospf-intf-event-tracking-actions-top {
        description
            "OSPF interface tracking actions top level configuration";
        container actions {
            description
                "Container that holds interface actions for OSPF events tracking";
            container interfaces {
                description
                    "Container that holds interfaces configuration for OSPF events tracking";

                list interface {
                // when " ipi-interface:interfaces/interface/config/enable-switchport != '1' ";
                    key "name";
                    description
                        "Interface list that holds interfaces actions for OSPF events tracking";
                    leaf name  {
                        type  leafref {
                            path  "../config/name";
                        }
                        description "Attribute used to specify the interface name for OSPF interface
                                    tracking event action.";
                    } // END of name definition.

                    container config {
                        description
                            "Configuration data for interface action";
                        uses ospf-intf-event-tracking-actions-config;
                    } // END of config-container definition.
                    container state {
                        config false;
                        description
                            "Operational state data for interface action";
                        uses ospf-intf-event-tracking-actions-config;
                    } // END of state-container definition.
                } // End of interface-list
            } // END of interfaces-container definition.
        } // END of actions-container definition.
    } // END of ospf-intf-event-tracking-actions-top definition.
    grouping ospf-intf-event-tracking-config {
        description
            "OSPF interface tracking configuration";
        leaf event-name  {
            type  string {
                length "1..1965";
                pattern "[^?' =,>|]+";
            }
            description "Attribute used to specify the event-name for OSPF interface tracking.";
        } // END of event-name definition.

        leaf event-match-criteria  {
            type  ipi-ospf-interface-tracking-types:intf_track_match_type_t;
            mandatory true;
            description "Attribute used to specify the match criteria for OSPF interface
                        tracking event.";
        } // END of event-match-criteria definition.

        leaf-list event-neighbor-ip-address  {
            type  inet:ipv4-address;
            description "Attribute used to specify the event neighbor IP address for OSPF
                        interface tracking event.";
        } // END of event-neighbor-ip-address definition.

    } // END of ospf-intf-event-tracking-config definition.
    grouping ospf-intf-event-tracking-top {
        description
            "OSPF interface tracking top level configuration";

        list ospf-interface-events-tracking {
            key "event-name";
            description
                "List to hold all OSPF interfaces events tracking configuration";
            leaf event-name  {
                type  leafref {
                    path  "../config/event-name";
                }
                description "Attribute used to specify the event-name for OSPF interface tracking.";
            } // END of event-name definition.

            container config {
                description
                    "Configuration data for OSPF events tracking";
                uses ospf-intf-event-tracking-config;
            } // END of config-container definition.
            container state {
                config false;
                description
                    "Operational state data for OSPF events tracking";
                uses ospf-intf-event-tracking-config;
            } // END of state-container definition.
            uses ospf-intf-event-tracking-actions-top;
        } // End of ospf-interface-events-tracking-list
    } // END of ospf-intf-event-tracking-top definition.

    grouping  ospf-interfaces-events-tracking-grouping {
    description
        "Container for all OSPF interfaces events tracking configuration";
    container ospf-interfaces-events-tracking {
        description
            "Container for all OSPF interfaces events tracking configuration";
        uses ospf-intf-event-tracking-top;
    } // END of ospf-interfaces-events-tracking-container definition.
    } // END of ospf-interfaces-events-tracking-grouping definition.

    uses ospf-interfaces-events-tracking-grouping;

}

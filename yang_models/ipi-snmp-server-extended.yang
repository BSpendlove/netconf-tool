/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-snmp-server-extended.yang
*
*/

module ipi-snmp-server-extended {

    yang-version 1.1;

    namespace   "http://www.ipinfusion.com/yang/ocnos/ipi-snmp-server-extended";

    prefix "ipi-snmp-server-extended";

    import cml-data-types {
        prefix cml-data-types;
        revision-date 2022-04-04;
    }

    import ipi-snmp {
        prefix ipi-snmp;
        revision-date 2021-07-28;
    }

    import ipi-snmp-server {
        prefix ipi-snmp-server;
        revision-date 2021-12-15;
    }

    import ipi-snmp-server-extended-types {
        prefix ipi-snmp-server-extended-types;
        revision-date 2022-03-20;
    }

    import ipi-acl {
        prefix ipi-acl;
        revision-date 2022-01-20;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "This module provides Simple Network Management Protocol server
                configuration";


    revision "2022-04-11" {
        description "Remove acl leaf from choice structure in SNMP community";
        reference " 0.2.5.";
    }

    revision "2022-04-05" {
        description "Moved community context mapping cli out of config container";
        reference " 0.2.4.";
    }

    revision "2022-03-10" {
        description "Added new cli's for SNMP context support";
        reference " 0.2.3.";
    }

    revision "2022-01-20" {
        description "New leafrefs re-added and some new flags";
        reference " 0.2.2.";
    }

    revision "2021-12-15" {
        description "New if-feature HAVE_HOSTPD added";
        reference " 0.2.1.";
    }

    revision "2021-11-16" {
        description "Module restructuring";
        reference " 0.2.0.";
    }

    revision "2018-06-21" {
        description "Initial Version";
        reference " 0.1.0.";
    }

    grouping snmp-server-debug-state {
        description
            "SNMP server terminal debug state attributes";
        leaf terminal-debug-status  {
            type  cml-data-types:cml_on_off_t;
            description "Use this attribute to display SNMP server terminal debugging
                        information";
        } // END of terminal-debug-status definition.

    } // END of snmp-server-debug-state definition.
    grouping snmp-server-debug-config {
        description
            "SNMP server debug configuration attributes";
        leaf enable  {
            type  empty;
            description "Use this attribute to enable/disable SNMP server debugging";
        } // END of enable definition.

    } // END of snmp-server-debug-config definition.
    grouping snmp-server-view-oid-tree-config {
        description
            "SNMP server view OID configuration";
        leaf oid  {
            type  string {
                length "1..1965";
                pattern "[^?' =,>|]+";
            }
            description "Use this attribute to configure object identifier subtree to be
                        included or excluded from the view.
                        To identify the subtree, specify a text string consisting of numbers,
                        such as 1.3.6.2.4.";
        } // END of oid definition.

        leaf filter-type  {
            type  ipi-snmp-server-extended-types:snmp_server_oid_tree_t;
            mandatory true;
            description "Use this attribute to update oid tree filter type for a view entry.";
        } // END of filter-type definition.

    } // END of snmp-server-view-oid-tree-config definition.
    grouping snmp-server-view-oid-tree-top {
        description
            "SNMP server view oids top level configuration";
        container oid-trees {
            description
                "Container for SNMP servers views oid tree configuration";

            list oid-tree {
                if-feature feature-list:HAVE_SNMP_AGENT;
                key "oid";
                description
                    "SNMP server view oid list configuration";
                leaf oid  {
                    type  leafref {
                        path  "../config/oid";
                    }
                    description "Use this attribute to configure object identifier subtree to be
                                included or excluded from the view.
                                To identify the subtree, specify a text string consisting of numbers,
                                such as 1.3.6.2.4.";
                } // END of oid definition.

                container config {
                    presence "yes";
                    description
                        "Configuration data for SNMP server view oid";
                    uses snmp-server-view-oid-tree-config;
                } // END of config-container definition.
                container state {
                    config false;
                    description
                        "Operational state data for SNMP server view oid";
                    uses snmp-server-view-oid-tree-config;
                } // END of state-container definition.
            } // End of oid-tree-list
        } // END of oid-trees-container definition.
    } // END of snmp-server-view-oid-tree-top definition.
    grouping snmp-server-view-config {
        description
            "SNMP server view configuration";
        leaf view-name  {
            type  string {
                length "1..32";
                pattern "[^?' =,>|]+";
            }
            description "Use this attribute to create or update a view entry.";
        } // END of view-name definition.

    } // END of snmp-server-view-config definition.
    grouping snmp-server-view-top {
        description
            "SNMP server view top level configuration";

        list snmp-view {
        when " /ipi-snmp:snmp/ipi-snmp-server:servers/ipi-snmp-server:server/ipi-snmp-server-extended:snmp-views/ipi-snmp-server-extended:snmp-view/ipi-snmp-server-extended:oid-trees/ipi-snmp-server-extended:oid-tree/ipi-snmp-server-extended:config ";
            if-feature feature-list:HAVE_SNMP_AGENT;
            key "view-name";
            description
                "SNMP server view list configuration";
            leaf view-name  {
                type  leafref {
                    path  "../config/view-name";
                }
                description "Use this attribute to create or update a view entry.";
            } // END of view-name definition.

            container config {
                description
                    "Configuration data for SNMP server views";
                uses snmp-server-view-config;
            } // END of config-container definition.
            container state {
                config false;
                description
                    "Operational state data for SNMP server views";
                uses snmp-server-view-config;
            } // END of state-container definition.
            uses snmp-server-view-oid-tree-top;
        } // End of snmp-view-list
    } // END of snmp-server-view-top definition.
    grouping snmp-server-host-config {
        description
            "SNMP server host configuration";
        leaf host-name  {
            type  string {
                length "1..63";
                pattern "[^?' =,>|]+";
            }
            description "Use this attribute to configure an SNMP trap host. An SNMP trap host
                        is usually a network management station (NMS) or an SNMP manager.";
        } // END of host-name definition.

        leaf snmp-version  {
            when " ../community or ../snmpv3-auth-type ";
            type  ipi-snmp-server-extended-types:snmp_server_version_t;
            description "Use this attribute to specify snmp-version to be used with host
                        configuration.";
        } // END of snmp-version definition.

        leaf notification-type  {
            when " ../community or ../snmpv3-auth-type ";
            type  ipi-snmp-server-extended-types:snmp_server_notification_t;
            description "Use this attribute to define the type of SNMP notification to the
                        host.
                        Specify to send informs or send traps.";
        } // END of notification-type definition.

        leaf udp-port  {
            when " ../community or ../snmpv3-auth-type or ../host-user ";
            type  uint32 {
                 range "1..65535"  {
                    description "1..65535:The notification hosts UDP port number";
                 }
            }
            description "Use this attribute to specify the port to be used when SNMP sends
                        packets to host.
                        The default is 162.";
        } // END of udp-port definition.

        choice host-option {
            description
                "host-option";
            case use-community {

                description
                    "Configure community";

                leaf community  {
                    when " ../snmp-version='1' or ../snmp-version='2' ";
                    type  leafref {
                        path  "/ipi-snmp:snmp/ipi-snmp-server:servers/ipi-snmp-server:server/communities/community/community-name";
                    }
                    description "Use this attribute to point to a pre-configured community. This can be
                                configured when SNMP version is 1 or 2c.";
                } // END of community definition.

            }
            case use-snmpv3-user {

                description
                    "Configure SNMPv3 user and authentication";

                leaf snmpv3-auth-type  {
                    when " ../snmp-version='3' + ../snmpv3-user ";
                    type  ipi-snmp-server-extended-types:snmp_server_version3_auth_type_t;
                    description "Use this attribute to configure the snmpv3 authentication type.
                                This can be configured only with SNMP version 3.";
                } // END of snmpv3-auth-type definition.

                leaf snmpv3-user  {
                    when " ../snmp-version='3' + ../snmpv3-auth-type ";
                    type  leafref {
                        path  "/ipi-snmp:snmp/ipi-snmp-server:servers/ipi-snmp-server:server/users/user/config/user-name";
                    }
                    description "Use this attribute to point to a pre-configured SNMPv3 user. This can
                                be configured when SNMP version is 3.";
                } // END of snmpv3-user definition.

            }
            case use-host-user {

                description
                    "Configure community or SNMPv3 user as host-user";

                leaf host-user  {
                    when " not(../snmp-version) ";
                    type  string {
                        length "1..1965";
                        pattern "[^?' =,>|]+";
                    }
                    description "Use this attribute to point to a pre-configured community or SNMPv3
                                user.";
                } // END of host-user definition.

            }
        } // END of host-option-choice definition.
    } // END of snmp-server-host-config definition.
    grouping snmp-server-host-top {
        description
            "SNMP server host top level configuration";

        list host {
            if-feature feature-list:HAVE_SNMP_AGENT;
            key "host-name";
            max-elements 8;
            description
                "SNMP server host list configuration";
            leaf host-name  {
                type  leafref {
                    path  "../config/host-name";
                }
                description "Use this attribute to configure an SNMP trap host. An SNMP trap host
                            is usually a network management station (NMS) or an SNMP manager.";
            } // END of host-name definition.

            container config {
                description
                    "Configuration data for SNMP server host configuration";
                uses snmp-server-host-config;
            } // END of config-container definition.
            container state {
                config false;
                description
                    "Operational state data for SNMP server host configuration";
                uses snmp-server-host-config;
            } // END of state-container definition.
        } // End of host-list
    } // END of snmp-server-host-top definition.
    grouping snmp-server-user-config {
        description
            "SNMP server user configuration";
        leaf user-name  {
            type  string {
                length "5..32";
                pattern "[^?' =,>|]+";
            }
            description "Use this attribute to create an SNMP server user.";
        } // END of user-name definition.

        leaf user-type  {
            type  ipi-snmp-server-extended-types:snmp_server_group_name_t;
            description "Use this attribute to create an SNMP server user of specified type.";
        } // END of user-type definition.

        leaf user-group  {
            type  string {
                length "1..1965";
                pattern "[^?' =,>|]+";
            }
            description "Use this attribute to add an SNMP server user to a group.";
        } // END of user-group definition.

        leaf encryption-type  {
            type  ipi-snmp-server-extended-types:snmp_server_key_type_t;
            description "Use this attribute to create an SNMP server user of specified
                        encryption type.
                        Use plain, to specify authentication-password and/or
                        privilege-password in plain text.
                        Use encrypt to specify authentication-password and/or
                        privilege-password in encrypted form.
                        This option is provided for reconfiguring a password using an earlier
                        encrypted password that was available
                        in running configuration display or get-config payload. Users are
                        advised not to use this option
                        for entering passwords generated in any other method.";
        } // END of encryption-type definition.

        leaf authentication-type  {
            when " ../authentication-password ";
            type  ipi-snmp-server-extended-types:snmp_server_auth_t;
            description "Use this attribute to create an SNMP server user of specified
                        authentication type.";
        } // END of authentication-type definition.

        leaf authentication-password  {
            when " ../encryption-type + ../authentication-type ";
            type  string {
                length "1..1965";
                pattern "[^?' =,>|]+";
            }
            description "Use this attribute to create an SNMP server user with an
                        authentication password.";
        } // END of authentication-password definition.

        leaf privilege-type  {
            when " ../privilege-password ";
            type  ipi-snmp-server-extended-types:snmp_server_priv_t;
            description "Use this attribute to create an SNMP server user of specified
                        privilege type.";
        } // END of privilege-type definition.

        leaf privilege-password  {
            when " ../encryption-type + ../privilege-type ";
            type  string {
                length "1..1965";
                pattern "[^?' =,>|]+";
            }
            description "Use this attribute to create an SNMP server user with a privilege
                        password.";
        } // END of privilege-password definition.

    } // END of snmp-server-user-config definition.
    grouping snmp-server-context-config {
        description
            "SNMP server context configuration";
        leaf context-name  {
            type  string {
                length "1..32";
                pattern "[^?' =,>|]+";
            }
            description "Use this attribute to create an SNMP server context";
        } // END of context-name definition.

    } // END of snmp-server-context-config definition.
    grouping snmp-server-context-top {
        description
            "SNMP server context top level configuration";

        list context {
            key "context-name";
            description
                "SNMP server context list configuration";
            leaf context-name  {
                type  leafref {
                    path  "../config/context-name";
                }
                description "Use this attribute to create an SNMP server context";
            } // END of context-name definition.

            container config {
                description
                    "Configuration data for SNMP server context";
                uses snmp-server-context-config;
            } // END of config-container definition.
            container state {
                config false;
                description
                    "Operational state data for SNMP server context";
                uses snmp-server-context-config;
            } // END of state-container definition.
        } // End of context-list
    } // END of snmp-server-context-top definition.
    grouping snmp-server-user-top {
        description
            "SNMP server user top level configuration";

        list user {
            if-feature feature-list:HAVE_SNMP_AGENT;
            if-feature feature-list:HAVE_SNMP_V3;
            key "user-name";
            description
                "SNMP server user list configuration";
            leaf user-name  {
                type  leafref {
                    path  "../config/user-name";
                }
                description "Use this attribute to create an SNMP server user.";
            } // END of user-name definition.

            container config {
                description
                    "Configuration data for SNMP server users";
                uses snmp-server-user-config;
            } // END of config-container definition.
            container state {
                config false;
                description
                    "Operational state data for SNMP server users";
                uses snmp-server-user-config;
            } // END of state-container definition.
        } // End of user-list
    } // END of snmp-server-user-top definition.
    grouping snmp-server-community-view-config {
        description
            "SNMP server commmunity view configuration";
        leaf community-view-name  {
            when " ../version and ../access ";
            type  leafref {
                path  "/ipi-snmp:snmp/ipi-snmp-server:servers/ipi-snmp-server:server/snmp-views/snmp-view/view-name";
            }
            description "Name of snmp view for a snmp community";
        } // END of community-view-name definition.

        leaf version  {
            when " ../community-view-name and ../access ";
            type  ipi-snmp-server-extended-types:snmp_server_view_version_t;
            description "Use this attribute set SNMP version to this community view.";
        } // END of version definition.

        leaf access  {
            when " ../community-view-name and ../version ";
            type  ipi-snmp-server-extended-types:snmp_server_access_t;
            description "Use this attribute to set access privileges to this community view.";
        } // END of access definition.

    } // END of snmp-server-community-view-config definition.
    grouping snmp-server-group-config {
        description
            "SNMP server group configuration";
        leaf group-name  {
            type  string {
                length "1..32";
                pattern "[^?' =,>|]+";
            }
            description "Use this attribute to create an SNMP group string.";
        } // END of group-name definition.

        leaf group-version  {
            type  ipi-snmp-server-extended-types:snmp_server_version_t;
            description "Use this attribute to specify group-version to be used with group
                        configuration.";
        } // END of group-version definition.

        leaf snmpv3-group-auth-type  {
            when " ../group-version='3' ";
            type  ipi-snmp-server-extended-types:snmp_v3_server_group_auth_type_t;
            description "Use this attribute to configure the snmpv3 authentication type.
                        This can be configured only with SNMP version 3.";
        } // END of snmpv3-group-auth-type definition.

        leaf-list context  {
            type  ipi-snmp-server-extended-types:snmp_server_context_name_t;
            description "Use this attribute to create an SNMP server context";
        } // END of context definition.

    } // END of snmp-server-group-config definition.
    grouping snmp-server-community-config {
        description
            "SNMP server commmunity configuration";
        leaf community-name  {
            type  string {
                length "1..32";
                pattern "[^?' =,>|]+";
            }
            description "Use this attribute to create an SNMP community string and access
                        privileges.";
        } // END of community-name definition.

        leaf acl-name  {
            when " /ipi-acl:acl/ipi-acl:standard-acl-sets/ipi-acl:standard-acl-set/ipi-acl:type = '6' ";
            type  leafref {
                path  "/ipi-acl:acl/ipi-acl:standard-acl-sets/ipi-acl:standard-acl-set/ipi-acl:name";
            }
            description "Use this attribute to create an SNMP community string and user-acl.";
        } // END of acl-name definition.

        choice community-option {
            description
                "community-option";
            case use-group {

                description
                    "Configure community group";

                leaf snmp-group  {
                    type  ipi-snmp-server-extended-types:snmp_server_group_t;
                    description "Use this attribute to create an SNMP community string with group.";
                } // END of snmp-group definition.

            }
            case use-access {

                description
                    "Configure community access privileges";

                leaf access-privileges  {
                    type  ipi-snmp-server-extended-types:snmp_server_access_t;
                    description "Use this attribute to create an SNMP community string and access
                                privileges.";
                } // END of access-privileges definition.

            }
            case use-view {

                description
                    "Configure community pointing to a snmp view";

                uses snmp-server-community-view-config;
            }
        } // END of community-option-choice definition.
    } // END of snmp-server-community-config definition.
    grouping snmp-server-community-context {
        description
            "SNMP server community context mapping configuration";
        leaf community-context  {
            type  leafref {
                path  "/ipi-snmp:snmp/ipi-snmp-server:servers/ipi-snmp-server:server/contexts/context/config/context-name";
            }
            description "Use this attribute to map a community with an SNMP server context";
        } // END of community-context definition.

        leaf community-user  {
            type  leafref {
                path  "/ipi-snmp:snmp/ipi-snmp-server:servers/ipi-snmp-server:server/users/user/config/user-name";
            }
            description "Use this attribute to point to a pre-configured SNMPv3 user. This can
                        be configured when SNMP version is 3.";
        } // END of community-user definition.

    } // END of snmp-server-community-context definition.
    grouping snmp-community-context-mapping {
        description
            "SNMP server community context mapping configuration";
        container community-context-mapping {
            description
                "SNMP server community context mapping configuration";
            container config {
                description
                    "SNMP server community context mapping configuration";
                uses snmp-server-community-context;
            } // END of config-container definition.
            container state {
                config false;
                description
                    "Community context mapping state data";
                uses snmp-server-community-context;
            } // END of state-container definition.
        } // END of community-context-mapping-container definition.
    } // END of snmp-community-context-mapping definition.
    grouping snmp-server-group-top {
        description
            "SNMP server group top level configuration";

        list server-group {
            if-feature feature-list:HAVE_SNMP_AGENT;
            key "group-name";
            description
                "Group list configuration";
            leaf group-name  {
                type  leafref {
                    path  "../config/group-name";
                }
                description "Use this attribute to create an SNMP group string.";
            } // END of group-name definition.

            container config {
                description
                    "Configuration data for SNMP Server server-groups";
                uses snmp-server-group-config;
            } // END of config-container definition.
            container state {
                config false;
                description
                    "Operational state data for SNMP Server Communities";
                uses snmp-server-group-config;
            } // END of state-container definition.
        } // End of server-group-list
    } // END of snmp-server-group-top definition.
    grouping snmp-server-community-top {
        description
            "SNMP server commmunity top level configuration";

        list community {
            if-feature feature-list:HAVE_SNMP_AGENT;
            key "community-name";
            description
                "Communities list configuration";
            leaf community-name  {
                type  leafref {
                    path  "../config/community-name";
                }
                description "Use this attribute to create an SNMP community string and access
                            privileges.";
            } // END of community-name definition.

            container config {
                description
                    "Configuration data for SNMP Server Communities";
                uses snmp-server-community-config;
            } // END of config-container definition.
            container state {
                config false;
                description
                    "Operational state data for SNMP Server Communities";
                uses snmp-server-community-config;
            } // END of state-container definition.
            uses snmp-community-context-mapping;
        } // End of community-list
    } // END of snmp-server-community-top definition.
    grouping snmp-statistics-state {
        description
            "SNMP statistics state";
        leaf engine-id  {
            type  cml-data-types:cml_line_t {
                length "1..1965";
            }
            description "snmp engine-id";
        } // END of engine-id definition.

    } // END of snmp-statistics-state definition.

    grouping  debug-grouping {
    description
        "Container for SNMP servers debug configuration";
    container debug {
        description
            "Container for SNMP servers debug configuration";
        container config {
            description
                "Configuration data for SNMP server debug configuration";
            uses snmp-server-debug-config;
        } // END of config-container definition.
        container state {
            config false;
            description
                "Operational state data for SNMP server debug configuration";
            uses snmp-server-debug-config;
            uses snmp-server-debug-state;
        } // END of state-container definition.
    } // END of debug-container definition.
    } // END of debug-grouping definition.

    grouping  snmp-views-grouping {
    description
        "Container for SNMP servers views configuration";
    container snmp-views {
        description
            "Container for SNMP servers views configuration";
        uses snmp-server-view-top;
    } // END of snmp-views-container definition.
    } // END of snmp-views-grouping definition.

    grouping  hosts-grouping {
    description
        "Container for SNMP servers hosts configuration";
    container hosts {
        description
            "Container for SNMP servers hosts configuration";
        uses snmp-server-host-top;
    } // END of hosts-container definition.
    } // END of hosts-grouping definition.

    grouping  users-grouping {
    description
        "Container for SNMP servers users configuration";
    container users {
        description
            "Container for SNMP servers users configuration";
        uses snmp-server-user-top;
    } // END of users-container definition.
    } // END of users-grouping definition.

    grouping  contexts-grouping {
    description
        "Container for SNMP servers contexts configuration";
    container contexts {
        description
            "Container for SNMP servers contexts configuration";
        uses snmp-server-context-top;
    } // END of contexts-container definition.
    } // END of contexts-grouping definition.

    grouping  communities-grouping {
    description
        "Container for SNMP servers communities configuration";
    container communities {
        description
            "Container for SNMP servers communities configuration";
        uses snmp-server-community-top;
    } // END of communities-container definition.
    } // END of communities-grouping definition.

    grouping  server-groups-grouping {
    description
        "Container for SNMP servers groups configuration";
    container server-groups {
        description
            "Container for SNMP servers groups configuration";
        uses snmp-server-group-top;
    } // END of server-groups-container definition.
    } // END of server-groups-grouping definition.

    grouping  statistics-grouping {
    description
        "Container for SNMP statistics";
    container statistics {
        config false;
        description
            "Container for SNMP statistics";
        container state {
            config false;
            description
                "Operational state data for SNMP statistics";
            uses snmp-statistics-state;
        } // END of state-container definition.
    } // END of statistics-container definition.
    } // END of statistics-grouping definition.

    augment /ipi-snmp:snmp/ipi-snmp-server:servers {
        if-feature feature-list:HAVE_SNMP_AGENT;
        description
            "Container for SNMP servers debug configuration";
        uses debug-grouping;
    }

    augment /ipi-snmp:snmp/ipi-snmp-server:servers/ipi-snmp-server:server {
        if-feature feature-list:HAVE_SNMP_AGENT;
        description
            "Container for SNMP servers views configuration";
        uses snmp-views-grouping;
    }

    augment /ipi-snmp:snmp/ipi-snmp-server:servers/ipi-snmp-server:server {
        if-feature feature-list:HAVE_SNMP_AGENT;
        description
            "Container for SNMP servers hosts configuration";
        uses hosts-grouping;
    }

    augment /ipi-snmp:snmp/ipi-snmp-server:servers/ipi-snmp-server:server {
        if-feature feature-list:HAVE_SNMP_AGENT;
        description
            "Container for SNMP servers users configuration";
        uses users-grouping;
    }

    augment /ipi-snmp:snmp/ipi-snmp-server:servers/ipi-snmp-server:server {
        if-feature feature-list:HAVE_SNMP_AGENT;
        description
            "Container for SNMP servers contexts configuration";
        uses contexts-grouping;
    }

    augment /ipi-snmp:snmp/ipi-snmp-server:servers/ipi-snmp-server:server {
        if-feature feature-list:HAVE_SNMP_AGENT;
        description
            "Container for SNMP servers communities configuration";
        uses communities-grouping;
    }

    augment /ipi-snmp:snmp/ipi-snmp-server:servers/ipi-snmp-server:server {
        if-feature feature-list:HAVE_SNMP_AGENT;
        description
            "Container for SNMP servers groups configuration";
        uses server-groups-grouping;
    }

    augment /ipi-snmp:snmp {
        if-feature feature-list:HAVE_SNMP_AGENT;
        description
            "Container for SNMP statistics";
        uses statistics-grouping;
    }


}

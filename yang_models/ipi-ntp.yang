/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ntp.yang
*
*/

module ipi-ntp {

    yang-version 1.1;

    namespace   "http://www.ipinfusion.com/yang/ocnos/ipi-ntp";

    prefix "ipi-ntp";

    import ietf-inet-types {
        prefix inet;
        revision-date 2013-07-15;
    }

    import cml-data-types {
        prefix cml-data-types;
        revision-date 2022-04-04;
    }

    import ipi-interface {
        prefix ipi-interface;
        revision-date 2022-04-05;
    }

    import ipi-network-instance {
        prefix ipi-network-instance;
        revision-date 2021-11-10;
    }

    import ipi-vrf {
        prefix ipi-vrf;
        revision-date 2021-09-03;
    }

    import ipi-ntp-types {
        prefix ipi-ntp-types;
        revision-date 2021-09-03;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for NTP configurations";


    revision "2022-02-16" {
        description "Introduced requestkey attribute to support nomodify option";
        reference " 0.5.0.";
    }

    revision "2021-10-08" {
        description "Updated dependencies for ntp global configurations";
        reference " 0.4.0.";
    }

    revision "2021-09-30" {
        description "Added validation utils function for peer-address attribute";
        reference " 0.3.0.";
    }

    revision "2021-09-06" {
        description "Added changes to make NTP feature disable persistent across device reloads";
        reference " 0.2.0.";
    }

    revision "2021-06-25" {
        description "Initial Version";
        reference " 0.1.0.";
    }

    grouping ntp-global-config {
        description
            "ntp global configuration";
        leaf source-interface  {
            when " /ipi-ntp:ntp/ipi-ntp:vrfs/ipi-ntp:vrf/ipi-ntp:config/ipi-ntp:enable-ntp = '1' + /ipi-ntp:ntp/ipi-ntp:vrfs/ipi-ntp:vrf/ipi-ntp:config/ipi-ntp:feature-enable ";
            type  leafref {
                path  "/ipi-interface:interfaces/ipi-interface:interface/ipi-interface:config/ipi-interface:name";
            }
            description "Use this attribute to specify the source interface for NTP packets";
        } // END of source-interface definition.

    } // END of ntp-global-config definition.
    grouping ntp-global-top {
        description
            "Top level container for ntp global configuration";
        container global {
            description
                "NTP global configuration";
            container config {
                description
                    "NTP global configuration";
                uses ntp-global-config;
            } // END of config-container definition.
            container state {
                config false;
                description
                    "Global NTP Operational state data";
                uses ntp-global-config;
            } // END of state-container definition.
        } // END of global-container definition.
    } // END of ntp-global-top definition.
    grouping ntp-vrf-config {
        description
            "ntp vrf configuration";
        leaf vrf-name  {
            type  leafref {
                path  "/ipi-network-instance:network-instances/ipi-network-instance:network-instance/ipi-vrf:vrf/ipi-vrf:config/ipi-vrf:vrf-name";
            }
            description "Use this attribute to specify the vrf for which ntp feature is enabled";
        } // END of vrf-name definition.

        leaf feature-enable  {
            type  boolean;
            description "Use this attribute to enable or disable NTP feature.";
        } // END of feature-enable definition.

        leaf enable-ntp  {
            when " /ipi-ntp:ntp/ipi-ntp:vrfs/ipi-ntp:vrf/ipi-ntp:config/ipi-ntp:feature-enable = '1' ";
            type  boolean;
            description "Use this attribute to enable or disable NTP server";
        } // END of enable-ntp definition.

        leaf enable-logging  {
            when " /ipi-ntp:ntp/ipi-ntp:vrfs/ipi-ntp:vrf/ipi-ntp:config/ipi-ntp:feature-enable = '1' ";
            type  empty;
            description "Use this attribute to log NTP events.";
        } // END of enable-logging definition.

    } // END of ntp-vrf-config definition.
    grouping ntp-ref-clock-master-config {
        description
            "ntp master clock  configuration";
        leaf enable-local-master  {
            type  empty;
            mandatory true;
            description "Use this attribute to configure the device as an NTP server.";
        } // END of enable-local-master definition.

        leaf local-stratum  {
            when " /ipi-ntp:ntp/ipi-ntp:vrfs/ipi-ntp:vrf/ipi-ntp:ref-clock-master/ipi-ntp:config/ipi-ntp:enable-local-master ";
            type  uint8 {
                 range "1..15"  {
                    description "1..15:Stratum level";
                 }
            }
            description "Use this attribute to configure stratum level for a NTP server.";
        } // END of local-stratum definition.

    } // END of ntp-ref-clock-master-config definition.
    grouping ntp-auth-config {
        description
            "ntp authentication  configuration";
        leaf enable-ntp-auth  {
            type  empty;
            description "Use this attribute to enable NTP authentication.";
        } // END of enable-ntp-auth definition.

        leaf-list ntp-trusted-keys  {
            type  uint32 {
                 range "1..65535"  {
                    description "1..65535:Key number";
                 }
            }
            description "Use this attribute to configure one or more trusted authentication
                        keys. If a key is trusted, the device will synchronize with a system
                        that specifies this key in its NTP packets";
        } // END of ntp-trusted-keys definition.

        leaf ntp-request-key  {
            when " /ipi-ntp:ntp/ipi-ntp:vrfs/ipi-ntp:vrf/ipi-ntp:authentication/ipi-ntp:config/ipi-ntp:ntp-trusted-keys ";
            type  uint32 {
                 range "1..65534"  {
                    description "1..65534:Key number";
                 }
            }
            description "Use this to attribute to configure request key which shall be used as
                        password for ntpdc utility.";
        } // END of ntp-request-key definition.

    } // END of ntp-auth-config definition.
    grouping ntp-auth-key-config {
        description
            "ntp authentication keys configuration";
        leaf key-id  {
            type  uint32 {
                 range "1..65535"  {
                    description "1..65535:Authentication key number (range 1-65535)";
                 }
            }
            description "Use this attribute to set an NTP authentication key id.";
        } // END of key-id definition.

        leaf key-value  {
            type  string {
                length "1..1965";
                pattern "[^?' =,>|]+";
            }
            mandatory true;
            description "Use this attribute to set an NTP authentication key value.";
        } // END of key-value definition.

        leaf key-type  {
            type  ipi-ntp-types:ntp_hostp_key_type_t;
            mandatory true;
            description "Use this attribute to set the NTP authentication key type.";
        } // END of key-type definition.

    } // END of ntp-auth-key-config definition.
    grouping ntp-server-config {
        description
            "ntp server configuration";
        leaf server-address  {
            type  string {
                length "1..63";
                pattern "[^?' =,>|]+";
            }
            description "Use this attribute to set the NTP server IP address or hostname";
        } // END of server-address definition.

    } // END of ntp-server-config definition.
    grouping ntp-peer-config {
        description
            "ntp server configuration";
        leaf peer-address  {
            type  string {
                length "1..63";
                pattern "[^?' =,>|]+";
            }
            description "Use this attribute to set the NTP peer IP address or hostname";
        } // END of peer-address definition.

    } // END of ntp-peer-config definition.
    grouping ntp-server-peer-common-config {
        description
            "common attributes for ntp server and peer configuration";
        leaf prefer  {
            type  empty;
            description "preferred NTP server/peer";
        } // END of prefer definition.

        leaf auth-key  {
            type  uint32 {
                 range "1..65535"  {
                    description "1..65535:Value of keyid 1-65535";
                 }
            }
            default "65535";
            description "Use this attribute to set the keyid to be used while communicating to
                        this server";
        } // END of auth-key definition.

        leaf minpoll  {
            type  uint16 {
                 range "4..16"  {
                    description "4..16:Poll interval in secs to a power of 2 [default 4]";
                 }
            }
            default "4";
            description "Use this attribute to set the minimum poll interval for NTP messages";
        } // END of minpoll definition.

        leaf maxpoll  {
            type  uint16 {
                 range "4..16"  {
                    description "4..16:Poll interval in secs to a power of 2 [default 6]";
                 }
            }
            default "6";
            description "Use this attribute to set the maximum poll interval for NTP messages";
        } // END of maxpoll definition.

    } // END of ntp-server-peer-common-config definition.
    grouping ntp-acl-config {
        description
            "NTP acl configuration";
        leaf client-ip-address  {
            type  inet:ip-address;
            description "use this attribute to specify the allowed NTP client IP address";
        } // END of client-ip-address definition.

        leaf netmask  {
            type  ipi-ntp-types:ntp_client_ip_net_mask_t;
            description "use this attribute to specify the allowed NTP client IP network mask";
        } // END of netmask definition.

        leaf access-options  {
            type  ipi-ntp-types:ntp_acl_options_t;
            description "use this attribute to specify the allowed access options for NTP
                        client";
        } // END of access-options definition.

    } // END of ntp-acl-config definition.
    grouping ntp-global-debug-config {
        description
            "NTP debug configuration";
        leaf enable  {
            type  empty;
            description "Use this attribute to enable NTP debug logs";
        } // END of enable definition.

    } // END of ntp-global-debug-config definition.
    grouping ntp-global-debug-state {
        description
            "NTP terminal debugging status";
        leaf terminal-debug-status  {
            type  cml-data-types:cml_on_off_t;
            description "This attribute contains the NTP terminal debug status";
        } // END of terminal-debug-status definition.

    } // END of ntp-global-debug-state definition.
    grouping ntp-rate-limiting-config {
        description
            "NTP ACL discard options";
        leaf minimum-pkt-spacing  {
            type  uint16 {
                 range "1..65535"  {
                    description "1..65535:minimum value in range [1-65535]";
                 }
            }
            description "Use this attribute to specify the minimum packet spacing to be
                        permitted";
        } // END of minimum-pkt-spacing definition.

    } // END of ntp-rate-limiting-config definition.
    grouping ntp-vrfs-top {
        description
            "Top level grouping for NTP VRF configuration and data";
        container vrfs {
            description
                "container for vrf level NTP configuration and state information";

            list vrf {
                key "vrf-name";
                description
                    "VRF level NTP configuration and state information";
                leaf vrf-name  {
                    type  leafref {
                        path  "../config/vrf-name";
                    }
                    description "Use this attribute to specify the vrf for which ntp feature is enabled";
                } // END of vrf-name definition.

                container config {
                    description
                        "NTP vrf configuration information";
                    uses ntp-vrf-config;
                } // END of config-container definition.
                container state {
                    config false;
                    description
                        "NTP vrf state information";
                    uses ntp-vrf-config;
                } // END of state-container definition.
                uses ntp-ref-clock-master-top;
                uses ntp-authentication-top;
                uses ntp-servers-top;
                uses ntp-peers-top;
                uses ntp-rate-limiting-top;
                uses ntp-access-control-entries-top;
            } // End of vrf-list
        } // END of vrfs-container definition.
    } // END of ntp-vrfs-top definition.
    grouping ntp-ref-clock-master-top {
        description
            "Top level grouping for NTP clock master configuration and state data";
        container ref-clock-master {
            when " /ipi-ntp:ntp/ipi-ntp:vrfs/ipi-ntp:vrf/ipi-ntp:config/ipi-ntp:feature-enable = '1' ";
            description
                "NTP clock master configuration and state data";
            container config {
                description
                    "NTP clock master configuration";
                uses ntp-ref-clock-master-config;
            } // END of config-container definition.
            container state {
                config false;
                description
                    "NTP clock master state data";
                uses ntp-ref-clock-master-config;
            } // END of state-container definition.
        } // END of ref-clock-master-container definition.
    } // END of ntp-ref-clock-master-top definition.
    grouping ntp-authentication-top {
        description
            "Top level grouping for NTP authentication configuration and state data";
        container authentication {
            when " /ipi-ntp:ntp/ipi-ntp:vrfs/ipi-ntp:vrf/ipi-ntp:config/ipi-ntp:feature-enable = '1' ";
            description
                "NTP authentication configuration and state data";
            container config {
                description
                    "NTP authentication configuration";
                uses ntp-auth-config;
            } // END of config-container definition.
            container state {
                config false;
                description
                    "NTP authentication state data";
                uses ntp-auth-config;
            } // END of state-container definition.
            uses ntp-authentication-keys-top;
        } // END of authentication-container definition.
    } // END of ntp-authentication-top definition.
    grouping ntp-authentication-keys-top {
        description
            "Top level grouping for NTP authentication key configuration and state
                        data";
        container ntp-keys {
            description
                "NTP authentication key configuration and state data";

            list ntp-key {
            when " /ipi-ntp:ntp/ipi-ntp:vrfs/ipi-ntp:vrf/ipi-ntp:config/ipi-ntp:feature-enable = '1' ";
                key "key-id";
                description
                    "NTP authentication key list";
                leaf key-id  {
                    type  leafref {
                        path  "../config/key-id";
                    }
                    description "Use this attribute to set an NTP authentication key.";
                } // END of key-id definition.

                container config {
                    description
                        "NTP authentication configuration";
                    uses ntp-auth-key-config;
                } // END of config-container definition.
                container state {
                    config false;
                    description
                        "NTP authentication state data";
                    uses ntp-auth-key-config;
                } // END of state-container definition.
            } // End of ntp-key-list
        } // END of ntp-keys-container definition.
    } // END of ntp-authentication-keys-top definition.
    grouping ntp-servers-top {
        description
            "Top level grouping for NTP server configuration and state data";
        container servers {
            description
                "Top level container for NTP server configuration and state data";

            list server {
            when " /ipi-ntp:ntp/ipi-ntp:vrfs/ipi-ntp:vrf/ipi-ntp:config/ipi-ntp:feature-enable = '1' ";
                key "server-address";
                description
                    "NTP servers configuration and state data";
                leaf server-address  {
                    type  leafref {
                        path  "../config/server-address";
                    }
                    description "Use this attribute to set the NTP server IP address or hostname";
                } // END of server-address definition.

                container config {
                    description
                        "NTP authentication configuration";
                    uses ntp-server-config;
                    uses ntp-server-peer-common-config;
                } // END of config-container definition.
                container state {
                    config false;
                    description
                        "NTP authentication state data";
                    uses ntp-server-config;
                    uses ntp-server-peer-common-config;
                } // END of state-container definition.
            } // End of server-list
        } // END of servers-container definition.
    } // END of ntp-servers-top definition.
    grouping ntp-peers-top {
        description
            "Top level grouping for NTP peer configuration and state data";
        container peers {
            description
                "Top level container for NTP peer configuration and state data";

            list peer {
            when " /ipi-ntp:ntp/ipi-ntp:vrfs/ipi-ntp:vrf/ipi-ntp:config/ipi-ntp:feature-enable = '1' ";
                key "peer-address";
                description
                    "NTP peers configuration and state data";
                leaf peer-address  {
                    type  leafref {
                        path  "../config/peer-address";
                    }
                    description "Use this attribute to set the NTP peer IP address or hostname";
                } // END of peer-address definition.

                container config {
                    description
                        "NTP authentication configuration";
                    uses ntp-peer-config;
                    uses ntp-server-peer-common-config;
                } // END of config-container definition.
                container state {
                    config false;
                    description
                        "NTP authentication state data";
                    uses ntp-peer-config;
                    uses ntp-server-peer-common-config;
                } // END of state-container definition.
            } // End of peer-list
        } // END of peers-container definition.
    } // END of ntp-peers-top definition.
    grouping ntp-rate-limiting-top {
        description
            "Top level grouping for NTP rate limit options";
        container rate-limiting {
            when " /ipi-ntp:ntp/ipi-ntp:vrfs/ipi-ntp:vrf/ipi-ntp:config/ipi-ntp:feature-enable = '1' + /ipi-ntp:ntp/ipi-ntp:vrfs/ipi-ntp:vrf/ipi-ntp:ref-clock-master/ipi-ntp:config/ipi-ntp:enable-local-master ";
            description
                "NTP rate limit options";
            container config {
                description
                    "NTP rate limiting options configuration";
                uses ntp-rate-limiting-config;
            } // END of config-container definition.
            container state {
                config false;
                description
                    "NTP authentication state data";
                uses ntp-rate-limiting-config;
            } // END of state-container definition.
        } // END of rate-limiting-container definition.
    } // END of ntp-rate-limiting-top definition.
    grouping ntp-access-control-entries-top {
        description
            "Top level grouping for NTP access control configuration and state data";
        container access-control-entries {
            when " /ipi-ntp:ntp/ipi-ntp:vrfs/ipi-ntp:vrf/ipi-ntp:ref-clock-master/ipi-ntp:config/ipi-ntp:enable-local-master ";
            description
                "NTP access control configuration and state data";

            list access-control-entry {
            when " /ipi-ntp:ntp/ipi-ntp:vrfs/ipi-ntp:vrf/ipi-ntp:config/ipi-ntp:feature-enable = '1' ";
                key "client-ip-address";
                description
                    "NTP access control list";
                leaf client-ip-address  {
                    type  leafref {
                        path  "../config/client-ip-address";
                    }
                    description "use this attribute to specify the allowed NTP client IP address";
                } // END of client-ip-address definition.

                container config {
                    description
                        "NTP access control configuration";
                    uses ntp-acl-config;
                } // END of config-container definition.
                container state {
                    config false;
                    description
                        "NTP access control state data";
                    uses ntp-acl-config;
                } // END of state-container definition.
            } // End of access-control-entry-list
        } // END of access-control-entries-container definition.
    } // END of ntp-access-control-entries-top definition.
    grouping ntp-debug-top {
        description
            "Top level grouping for NTP debug configuration and state data";
        container debug {
            description
                "NTP debug configuration and state data";
            container config {
                description
                    "NTP debug configuration";
                uses ntp-global-debug-config;
            } // END of config-container definition.
            container state {
                config false;
                description
                    "NTP access control state data";
                uses ntp-global-debug-config;
                uses ntp-global-debug-state;
            } // END of state-container definition.
        } // END of debug-container definition.
    } // END of ntp-debug-top definition.

    grouping  ntp-grouping {
    description
        "Top level container for NTP, including configuration and state data";
    container ntp {
        description
            "Top level container for NTP, including configuration and state data";
        uses ntp-global-top;
        uses ntp-vrfs-top;
        uses ntp-debug-top;
    } // END of ntp-container definition.
    } // END of ntp-grouping definition.

    uses ntp-grouping;

    rpc ntp-clear-statistics {
        description "Use this RPC to clear NTP statistics";
        input  {
            leaf statistics-type  {
                type ipi-ntp-types:ntp_statistics_type_t;
                mandatory true;
                description "Use this attribute to specify the type of NTP statistics that needs to
                            be cleared";
            }
        }
    }

    rpc ntp-retry-server-synchronization {
        description "Use this RPC to retry synchronization with the configured NTP servers";
        input  {
            leaf vrf-name  {
                type string;
                mandatory true;
                description "Use this attribute to specify the vrf name on which the
                            synchronization should be retried";
            }
        }
    }

    rpc ntp-terminal-debugging-on {
        description "Use this RPC to enable terminal NTP debugs";
    }

    rpc ntp-terminal-debugging-off {
        description "Use this RPC to disable terminal NTP debugs";
    }

}

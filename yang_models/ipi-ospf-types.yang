/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ospf-types.yang
*
*/

module ipi-ospf-types {

    yang-version 1.1;

    namespace   "http://www.ipinfusion.com/yang/ocnos/ipi-ospf-types";

    prefix "ipi-ospf-types";

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 OSPF types";


    revision "2022-01-07" {
        description "Defined New Data Type";
        reference " 0.3.0.";
    }

    revision "2021-10-25" {
        description "Added debug packet options type";
        reference " 0.2.4.";
    }

    revision "2021-09-20" {
        description "Fix the value for inactive mapping server status";
        reference " 0.2.3.";
    }

    revision "2021-09-03" {
        description "Update descriptions of attribute";
        reference " 0.2.2.";
    }

    revision "2021-08-18" {
        description "State attributes for Segment Routing, TI LFA and TE";
        reference " 0.2.1.";
    }

    revision "2021-07-28" {
        description "Add passive-interface address mode enum OSPF_PASSIVE_ADDR_MODE_T";
        reference " 0.2.0.";
    }

    revision "2021-05-22" {
        description "Add passive-interface mode enum OSPF_PASSIVE_MODE_T";
        reference " 0.1.3.";
    }

    revision "2021-05-05" {
        description "Add isis and ospf option to enum OSPF_ROUTE_SOURCE_TYPE_T";
        reference " 0.1.2.";
    }

    revision "2021-04-30" {
        description "Removed type OSPF_FILTER_LIST_DIRECTION_T";
        reference " 0.1.1.";
    }

    revision "2021-04-06" {
        description "Restructured module in accordance with OpenConfig style";
        reference " 0.1.0.";
    }



    typedef  ospf_md5_password_t {
        type string {
            pattern "[^? ]*";
        }
        description "type definition for OSPF_MD5_PASSWORD_T";
    }

    typedef  ospf_area_t {
        type union {
            type inet:ipv4-address {

            }
            type uint32 {
                range "0..4294967295";

            }
        }
        description "type definition for OSPF_AREA_T";
    }

    typedef  ospf_area_authentication_type_t {
        type enumeration {
            enum authentication {
                value 1;
                description "Enable authentication";
            }
            enum authentication-message-digest {
                value 2;
                description "Enable authentication,Use message-digest authentication";
            }
        }
        description "type definition for OSPF_AREA_AUTHENTICATION_TYPE_T";
    }

    typedef  ospf_if_authentication_type_t {
        type enumeration {
            enum null {
                value 0;
                description "Use no authentication";
            }
            enum simple {
                value 1;
                description "Use simple authentication";
            }
            enum message-digest {
                value 2;
                description "Use message-digest authentication";
            }
        }
        description "type definition for OSPF_IF_AUTHENTICATION_TYPE_T";
    }

    typedef  ospf_network_t {
        type enumeration {
            enum point-to-point {
                value 1;
                description "OSPF point-to-point network";
            }
            enum broadcast {
                value 2;
                description "OSPF broadcast multi-access network";
            }
            enum non-broadcast {
                value 3;
                description "OSPF NBMA network";
            }
            enum point-to-multipoint {
                value 4;
                description "OSPF point-to-multipoint network";
            }
            enum point-to-multipoint-non-broadcast {
                value 5;
                description "OSPF point-to-multipoint network,non-broadcast point-to-multipoint network";
            }
        }
        description "type definition for OSPF_NETWORK_T";
    }

    typedef  ospf_cipher_type_t {
        type enumeration {
            enum md5 {
                value 0;
                description "MD5 Encryption Algorithm";
            }
        }
        description "type definition for OSPF_CIPHER_TYPE_T";
    }

    typedef  ospf_abr_type_t {
        type enumeration {
            enum standard {
                value 1;
                description "Standard behavior (RFC2328)";
            }
            enum cisco {
                value 2;
                description "Cisco implementation (RFC3509)";
            }
            enum ibm {
                value 3;
                description "IBM implementation (RFC3509)";
            }
            enum shortcut {
                value 4;
                description "Shortcut ABR";
            }
        }
        description "type definition for OSPF_ABR_TYPE_T";
    }

    typedef  ospf_log_adj_opt_t {
        type enumeration {
            enum brief {
                value 0;
                description "Log state changes";
            }
            enum detail {
                value 1;
                description "Log all state changes";
            }
        }
        description "type definition for OSPF_LOG_ADJ_OPT_T";
    }

    typedef  ospf_cspf_tie_break_t {
        type enumeration {
            enum random {
                value 0;
                description "Random";
            }
            enum most-fill {
                value 1;
                description "Most fill";
            }
            enum least-fill {
                value 2;
                description "Least fill";
            }
        }
        description "type definition for OSPF_CSPF_TIE_BREAK_T";
    }

    typedef  ospf_frr_tie_break_t {
        type enumeration {
            enum primary-path {
                value 20;
                description "Prefer backup path from ECMP set \n\t     *Default value is 20\n";
            }
            enum node-protecting {
                value 30;
                description "Prefer node protecting backup path \n\t     *Default value is 30\n";
            }
            enum interface-disjoint {
                value 60;
                description "Prefer link protecting backup path \n\t     *Default value is 60\n";
            }
            enum broadcast-interface-disjoint {
                value 70;
                description "Prefer broadcast link protecting backup path \n\t\t\t        *Default value is 70\n";
            }
            enum downstream-path {
                value 90;
                description "Prefer backup path from downstream \n\t     *Default value is 90\n";
            }
            enum secondary-path {
                value 255;
                description "Prefer non-ECMP backup path \n\t\t\t        *Default value is 255\n";
            }
        }
        description "type definition for OSPF_FRR_TIE_BREAK_T";
    }

    typedef  ospf_domain_type_t {
        type enumeration {
            enum type-as {
                value 1;
                description "Type 0x0005";
            }
            enum type-as4 {
                value 2;
                description "Type 0x0205";
            }
            enum type-back-comp {
                value 3;
                description "Type 0x8005";
            }
            enum type-ip {
                value 4;
                description "Type 0x0105";
            }
        }
        description "type definition for OSPF_DOMAIN_TYPE_T";
    }

    typedef  ospf_translator_role_t {
        type enumeration {
            enum never {
                value 0;
                description "Do not translate";
            }
            enum always {
                value 1;
                description "Translate always";
            }
            enum candidate {
                value 2;
                description "Candidate for translator (default)";
            }
        }
        description "type definition for OSPF_TRANSLATOR_ROLE_T";
    }

    typedef  ospf_nssa_translator_state_t {
        type bits {
            bit enabled {
                position 1;
                description "OSPF NSSA Translator enabled";
            }
            bit elected {
                position 2;
                description "OSPF NSSA Translator elected";
            }
            bit disabled {
                position 3;
                description "OSPF NSSA Translator disabled";
            }
        }
        description "type definition for OSPF_NSSA_TRANSLATOR_STATE_T";
    }

    typedef  ospf_route_source_type_t {
        type enumeration {
            enum kernel {
                value 1;
                description "Kernel routes";
            }
            enum connected {
                value 2;
                description "Connected routes";
            }
            enum static {
                value 3;
                description "Static routes";
            }
            enum rip {
                value 4;
                description "Routing Information Protocol (RIP) routes";
            }
            enum ospf {
                value 6;
                description "ISO OSPF";
            }
            enum bgp {
                value 8;
                description "Border Gateway Protocol (BGP) routes";
            }
            enum isis {
                value 9;
                description "IS-IS routes";
            }
        }
        description "type definition for OSPF_ROUTE_SOURCE_TYPE_T";
    }

    typedef  ospf_prefix_route_type_t {
        type enumeration {
            enum unspecified {
                value 0;
                description "Unspecified route type";
            }
            enum intra-area {
                value 1;
                description "Intra-area route type";
            }
            enum inter-area {
                value 3;
                description "Inter-area route type";
            }
            enum as-external {
                value 5;
                description "Autonomus System External route type";
            }
            enum nssa-external {
                value 7;
                description "Not-So-Stubby Area External route type";
            }
        }
        description "type definition for OSPF_PREFIX_ROUTE_TYPE_T";
    }

    typedef  ospf_metric_type_t {
        type enumeration {
            enum 1 {
                value 1;
                description "Set OSPF External Type 1 metrics";
            }
            enum 2 {
                value 2;
                description "Set OSPF External Type 2 metrics";
            }
        }
        description "type definition for OSPF_METRIC_TYPE_T";
    }

    typedef  ospf_nssa_t {
        type enumeration {
            enum nssa {
                value 1;
                description "OSPF area as NSSA";
            }
        }
        description "type definition for OSPF_NSSA_T";
    }

    typedef  ospf_db_limit_type_t {
        type enumeration {
            enum soft {
                value 1;
                description "Soft limit";
            }
            enum hard {
                value 2;
                description "Hard limit";
            }
        }
        description "type definition for OSPF_DB_LIMIT_TYPE_T";
    }

    typedef  ospf_vlink_interface_state_t {
        type enumeration {
            enum DependUpon {
                value 0;
                description "IFSM DependUpon";
            }
            enum Down {
                value 1;
                description "IFSM Down";
            }
            enum Loopback {
                value 2;
                description "IFSM Loopback";
            }
            enum Waiting {
                value 3;
                description "IFSM Waiting";
            }
            enum Point-To-Point {
                value 4;
                description "IFSM Point-To-Point";
            }
            enum DROther {
                value 5;
                description "IFSM DROther";
            }
            enum Backup {
                value 6;
                description "IFSM Backup";
            }
            enum DR {
                value 7;
                description "IFSM DR";
            }
        }
        description "type definition for OSPF_VLINK_INTERFACE_STATE_T";
    }

    typedef  ospf_vlink_status_t {
        type enumeration {
            enum Down {
                value 0;
                description "Virtual Link Down";
            }
            enum Up {
                value 1;
                description "Virtual Link Up";
            }
        }
        description "type definition for OSPF_VLINK_STATUS_T";
    }

    typedef  ospf_vlink_adj_state_t {
        type enumeration {
            enum DependUpon {
                value 0;
                description "NFSM DependUpon";
            }
            enum Down {
                value 1;
                description "NFSM Down";
            }
            enum Attempt {
                value 2;
                description "NFSM Attempt";
            }
            enum Init {
                value 3;
                description "NFSM Init";
            }
            enum 2-Way {
                value 4;
                description "NFSM 2-Way";
            }
            enum ExStart {
                value 5;
                description "NFSM ExStart";
            }
            enum Exchange {
                value 6;
                description "NFSM Exchange";
            }
            enum Loading {
                value 7;
                description "NFSM Loading";
            }
            enum Full {
                value 8;
                description "NFSM Full";
            }
        }
        description "type definition for OSPF_VLINK_ADJ_STATE_T";
    }

    typedef  ospf_neighbor_state_change_t {
        type enumeration {
            enum down {
                value 1;
                description "Down";
            }
            enum attempt {
                value 2;
                description "Attempt";
            }
            enum init {
                value 3;
                description "Init";
            }
            enum twoWay {
                value 4;
                description "Two Way";
            }
            enum exchangeStart {
                value 5;
                description "Exchange Start";
            }
            enum exchange {
                value 6;
                description "Exchange";
            }
            enum loading {
                value 7;
                description "Loading";
            }
            enum full {
                value 8;
                description "Full";
            }
        }
        description "type definition for OSPF_NEIGHBOR_STATE_CHANGE_T";
    }

    typedef  ospf_domain_id_hex_string_t {
        type string {
            pattern "[0-9a-fA-F]{12}";
        }
        description "type definition for OSPF_DOMAIN_ID_HEX_STRING_T";
    }

    typedef  ospf_if_state {
        type enumeration {
            enum enabled {
                value 1;
                description "OSPF_API_STATUS_ENABLED";
            }
            enum disabled {
                value 2;
                description "OSPF_API_STATUS_DISABLED";
            }
        }
        description "type definition for OSPF_IF_STATE";
    }

    typedef  ospf_row_status {
        type enumeration {
            enum row-status-active {
                value 1;
                description "Active Row status";
            }
            enum row-status-notinservice {
                value 2;
                description "Row status Not in Service";
            }
            enum row-status-notready {
                value 3;
                description "Row status Not Ready";
            }
            enum row-status-createandgo {
                value 4;
                description "Row status Create and Go";
            }
            enum row-status-createandwait {
                value 5;
                description "Row status Create and Wait";
            }
        }
        description "type definition for OSPF_ROW_STATUS";
    }

    typedef  ospf_bfd_state {
        type enumeration {
            enum enable {
                value 0;
                description "Enable BFD";
            }
            enum disable {
                value 1;
                description "Disable BFD";
            }
        }
        description "type definition for OSPF_BFD_STATE";
    }

    typedef  ospf_area_shortcut_type_t {
        type enumeration {
            enum default {
                value 0;
                description "Set default shortcutting behavior";
            }
            enum enable {
                value 1;
                description "Enable shortcutting through the area";
            }
            enum disable {
                value 2;
                description "Disable shortcutting through the area";
            }
        }
        description "type definition for OSPF_AREA_SHORTCUT_TYPE_T";
    }

    typedef  ospf_debug_route_t {
        type bits {
            bit spf {
                position 0;
                description "SPF calculation information";
            }
            bit ia {
                position 1;
                description "Inter-Area route calculation information";
            }
            bit ase {
                position 2;
                description "External route calculation information";
            }
            bit install {
                position 3;
                description "Route installation information";
            }
            bit spf-terse {
                position 4;
                description "SPF Calculation terse information";
            }
        }
        description "type definition for OSPF_DEBUG_ROUTE_T";
    }

    typedef  ospf_debug_rib_t {
        type bits {
            bit interface {
                position 0;
                description "RIB interface";
            }
            bit redistribute {
                position 1;
                description "RIB redistribute";
            }
        }
        description "type definition for OSPF_DEBUG_RIB_T";
    }

    typedef  ospf_debug_packet_options_t {
        type bits {
            bit send {
                position 0;
                description "Packet sent";
            }
            bit recv {
                position 1;
                description "Packet received";
            }
            bit detail {
                position 2;
                description "Detail information";
            }
        }
        description "type definition for OSPF_DEBUG_PACKET_OPTIONS_T";
    }

    typedef  ospf_debug_nsm_t {
        type bits {
            bit interface {
                position 0;
                description "NSM interface";
            }
            bit redistribute {
                position 1;
                description "NSM redistribute";
            }
        }
        description "type definition for OSPF_DEBUG_NSM_T";
    }

    typedef  ospf_debug_nfsm_t {
        type bits {
            bit status {
                position 0;
                description "NFSM Status Information";
            }
            bit events {
                position 1;
                description "NFSM Event Information";
            }
            bit timers {
                position 2;
                description "NFSM Timers Information";
            }
        }
        description "type definition for OSPF_DEBUG_NFSM_T";
    }

    typedef  ospf_debug_lsa_t {
        type bits {
            bit generate {
                position 0;
                description "LSA Generation";
            }
            bit flooding {
                position 1;
                description "LSA Flooding";
            }
            bit install {
                position 2;
                description "LSA Installation";
            }
            bit refresh {
                position 3;
                description "LSA Refreshment";
            }
            bit maxage {
                position 4;
                description "LSA MaxAge processing";
            }
        }
        description "type definition for OSPF_DEBUG_LSA_T";
    }

    typedef  ospf_debug_ifsm_t {
        type bits {
            bit status {
                position 0;
                description "IFSM Status Information";
            }
            bit events {
                position 1;
                description "IFSM Event Information";
            }
            bit timers {
                position 2;
                description "IFSM Timers Information";
            }
        }
        description "type definition for OSPF_DEBUG_IFSM_T";
    }

    typedef  ospf_debug_event_t {
        type bits {
            bit abr {
                position 0;
                description "OSPF ABR events";
            }
            bit nssa {
                position 1;
                description "OSPF NSSA events";
            }
            bit asbr {
                position 2;
                description "OSPF ASBR events";
            }
            bit vlink {
                position 3;
                description "OSPF Virtual-Link events";
            }
            bit lsa {
                position 4;
                description "OSPF LSA events";
            }
            bit os {
                position 5;
                description "OSPF OS interaction events";
            }
            bit router {
                position 6;
                description "Other router events";
            }
        }
        description "type definition for OSPF_DEBUG_EVENT_T";
    }

    typedef  ospf_debug_redist_t {
        type bits {
            bit detail {
                position 0;
                description "OSPF redistribute Details";
            }
            bit terse {
                position 1;
                description "OSPF redistribute Terse";
            }
        }
        description "type definition for OSPF_DEBUG_REDIST_T";
    }

    typedef  ospf_debug_graceful_t {
        type bits {
            bit detail {
                position 0;
                description "OSPF graceful-restart Details";
            }
            bit terse {
                position 1;
                description "OSPF graceful-restart Terse";
            }
        }
        description "type definition for OSPF_DEBUG_GRACEFUL_T";
    }

    typedef  ospf_interface_state_t {
        type enumeration {
            enum down {
                value 1;
                description "down";
            }
            enum loopback {
                value 2;
                description "loopback";
            }
            enum waiting {
                value 3;
                description "waiting";
            }
            enum pointToPoint {
                value 4;
                description "pointToPoint";
            }
            enum designatedRouter {
                value 5;
                description "designatedRouter";
            }
            enum backupDesignatedRouter {
                value 6;
                description "backupDesignatedRouter";
            }
            enum otherDesignatedRouter {
                value 7;
                description "otherDesignatedRouter";
            }
        }
        description "type definition for OSPF_INTERFACE_STATE_T";
    }

    typedef  ospf_packet_type_t {
        type enumeration {
            enum hello {
                value 1;
                description "OSPF Hello";
            }
            enum db-desription {
                value 2;
                description "OSPF Database Description";
            }
            enum ls-request {
                value 3;
                description "OSPF Link State Request";
            }
            enum ls-update {
                value 4;
                description "OSPF Link State Update";
            }
            enum ls-ack {
                value 5;
                description "OSPF Link State Acknowledgment";
            }
        }
        description "type definition for OSPF_PACKET_TYPE_T";
    }

    typedef  ospf_lsdb_type_t {
        type enumeration {
            enum router-link {
                value 1;
                description "Router link";
            }
            enum network-link {
                value 2;
                description "Network link";
            }
            enum summary-link {
                value 3;
                description "Summary link";
            }
            enum as-summary-link {
                value 4;
                description "AS summary link";
            }
            enum as-external-link {
                value 5;
                description "AS external link";
            }
            enum multicast-link {
                value 6;
                description "Multicast link";
            }
            enum nssa-external-link {
                value 7;
                description "NSSA external link";
            }
            enum local-opaque-Link {
                value 9;
                description "local opaque link";
            }
            enum area-opaque-Link {
                value 10;
                description "area opaque link";
            }
            enum as-opaque-Link {
                value 11;
                description "AS opaque link";
            }
        }
        description "type definition for OSPF_LSDB_TYPE_T";
    }

    typedef  ospf_config_error_type_t {
        type enumeration {
            enum bad-version {
                value 1;
                description "Bad version";
            }
            enum area-mismatch {
                value 2;
                description "Area mismatch";
            }
            enum unknown-nbma-neighbor {
                value 3;
                description "Unknown NBMA neighbor";
            }
            enum unknown-virtual-neighbor {
                value 4;
                description "Unknown virtual neighbor";
            }
            enum auth-type-mismatch {
                value 5;
                description "Authentication type mismatch";
            }
            enum auth-failure {
                value 6;
                description "Authentication failure";
            }
            enum netmask-mismatch {
                value 7;
                description "Network mask mismatch";
            }
            enum hello-interval-mismatch {
                value 8;
                description "Hello interval mismatch";
            }
            enum dead-interval-mismatch {
                value 9;
                description "Dead interval mismatch";
            }
            enum option-mismatch {
                value 10;
                description "Option mismatch";
            }
            enum mtu-mismatch {
                value 11;
                description "Mtu mismatch";
            }
            enum duplicate-router-id {
                value 12;
                description "Duplicated router ID";
            }
            enum no-error {
                value 13;
                description "No error";
            }
        }
        description "type definition for OSPF_CONFIG_ERROR_TYPE_T";
    }

    typedef  ospf_dste_status {
        type enumeration {
            enum enabled {
                value 1;
                description "DSTE status enabled";
            }
            enum disabled {
                value 2;
                description "DSTE status disabled";
            }
        }
        description "type definition for OSPF_DSTE_STATUS";
    }

    typedef  ospf_passive_mode_t {
        type enumeration {
            enum disable {
                value 0;
                description "Disable passive interface";
            }
            enum enable {
                value 1;
                description "Enable passive interface";
            }
        }
        description "type definition for OSPF_PASSIVE_MODE_T";
    }

    typedef  ospf_passive_addr_mode_t {
        type enumeration {
            enum enable {
                value 1;
                description "Enable passive interface";
            }
        }
        description "type definition for OSPF_PASSIVE_ADDR_MODE_T";
    }

    typedef  ospf_resolution_policy_t {
        type enumeration {
            enum quarantine {
                value 0;
                description "Quarantine policy";
            }
        }
        description "type definition for OSPF_RESOLUTION_POLICY_T";
    }

    typedef  ospf_sr_mapping_server_status_t {
        type enumeration {
            enum init {
                value 0;
                description "Mapping server status init";
            }
            enum active {
                value 1;
                description "Mapping server status active";
            }
            enum inactive {
                value 2;
                description "Mapping server status inactive";
            }
        }
        description "type definition for OSPF_SR_MAPPING_SERVER_STATUS_T";
    }

    typedef  ospf_sr_algorithm_t {
        type enumeration {
            enum shortest-path {
                value 0;
                description "Segment Routing Shortest Path Algorithm";
            }
            enum strict-shortest-path {
                value 1;
                description "Segment Routing Strict Shortest Path Algorithm";
            }
        }
        description "type definition for OSPF_SR_ALGORITHM_T";
    }

    typedef  ospf_tlv_type_t {
        type enumeration {
            enum router-address {
                value 1;
                description "TLV router address type";
            }
            enum link {
                value 2;
                description "TLV link type";
            }
            enum router-ipv6-address {
                value 3;
                description "TLV router IPv6 address type";
            }
            enum link-local {
                value 4;
                description "TLV link-local type";
            }
        }
        description "type definition for OSPF_TLV_TYPE_T";
    }

    typedef  ospf_tlv_link_type_t {
        type enumeration {
            enum point-to-point {
                value 1;
                description "TLV point-to-point link type";
            }
            enum multi-access {
                value 2;
                description "TLV multi-access link type";
            }
        }
        description "type definition for OSPF_TLV_LINK_TYPE_T";
    }

}

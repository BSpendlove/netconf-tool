/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-radius.yang
*
*/

module ipi-radius {

    yang-version 1.1;

    namespace   "http://www.ipinfusion.com/yang/ocnos/ipi-radius";

    prefix "ipi-radius";

    import cml-data-types {
        prefix cml-data-types;
        revision-date 2022-04-04;
    }

    import ipi-radius-types {
        prefix ipi-radius-types;
        revision-date 2021-10-26;
    }

    import ipi-vrf {
        prefix ipi-vrf;
        revision-date 2021-09-03;
    }

    import ipi-network-instance {
        prefix ipi-network-instance;
        revision-date 2021-11-10;
    }

    import ietf-yang-types {
        prefix yang;
        revision-date 2013-07-15;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "Layer-3 radius configurations";


    revision "2021-10-26" {
        description "Restructured module as per open-config style";
        reference " 0.2.0.";
    }

    revision "2018-06-21" {
        description "Initial Version";
        reference " 0.1.0.";
    }

    grouping radius-global-config {
        description
            "RADIUS Global Configuration items";
        leaf vrf-name  {
            type  leafref {
                path  "/ipi-network-instance:network-instances/ipi-network-instance:network-instance/ipi-vrf:vrf/ipi-vrf:config/ipi-vrf:vrf-name";
            }
            description "VRF Name associated with this instance";
        } // END of vrf-name definition.

        leaf key-type  {
            type  ipi-radius-types:radius_hostp_key_type_t;
            description "Authentication key type";
        } // END of key-type definition.

        leaf secret-key-string  {
            when " /ipi-radius:radius/ipi-radius:vrfs/ipi-radius:vrf/ipi-radius:config/ipi-radius:key-type ";
            type  string {
                length "1..1965";
                pattern "[^?' =,>|]+";
            }
            description "Shared key used between the authentication-server and the device";
        } // END of secret-key-string definition.

        leaf timeout  {
            type  uint8 {
                 range "1..60"  {
                    description "1..60:RADIUS server global timeout period in seconds";
                 }
            }
            units "seconds";
            description "Use this attribute to set the global timeout which is how long the
                        device
                        waits for a response from a RADIUS server before declaring a timeout
                        failure";
        } // END of timeout definition.

    } // END of radius-global-config definition.
    grouping radius-server-config {
        description
            "RADIUS Server Configuration items";
        leaf host-address  {
            type  cml-data-types:cml_hostname_t;
            description "Use this attribute to set the RADIUS server hostname or IP address";
        } // END of host-address definition.

        leaf sequence-number  {
            type  uint8 {
                 range "1..8"  {
                    description "1..8:sequence number for servers";
                 }
            }
            mandatory true;
            description "Use this attribute to set the sequence-number/priority index
                        for the RADIUS server";
        } // END of sequence-number definition.

        leaf key-type  {
            type  ipi-radius-types:radius_hostp_key_type_t;
            description "Authentication key type";
        } // END of key-type definition.

        leaf secret-key-string  {
            when " /ipi-radius:radius/ipi-radius:vrfs/ipi-radius:vrf/ipi-radius:remote-servers/ipi-radius:server/ipi-radius:config/ipi-radius:key-type ";
            type  string {
                length "1..1965";
                pattern "[^?' =,>|]+";
            }
            description "Shared key used between the authentication-server and the device";
        } // END of secret-key-string definition.

        leaf accounting-port  {
            type  uint16 {
                 range "0..65535"  {
                    description "0..65535:RADIUS accounting port";
                 }
            }
            description "Use this attribute to configure a RADIUS server and specify a UDP port
                        to use for
                        RADIUS accounting messages";
        } // END of accounting-port definition.

        leaf authentication-port  {
            type  uint16 {
                 range "0..65535"  {
                    description "0..65535:RADIUS authentication port";
                 }
            }
            description "Use this attribute to configure a RADIUS server and specify a UDP port
                        to use for
                        RADIUS authentication messages";
        } // END of authentication-port definition.

        leaf timeout  {
            type  uint8 {
                 range "1..60"  {
                    description "1..60:RADIUS server timeout period in seconds";
                 }
            }
            units "seconds";
            default "5";
            description "To represent the timeout configured by the user";
        } // END of timeout definition.

    } // END of radius-server-config definition.
    grouping radius-counters-state {
        description
            "Grouping for RADIUS server counters";
        container counters {
            config false;
            description
                "RADIUS Server connection counters";
            leaf failed-authentications  {
                type  yang:counter32;
                description "RADIUS Server count for authentication failures";
            } // END of failed-authentications definition.

            leaf success-authentications  {
                type  yang:counter32;
                description "RADIUS Server count for successful authentications";
            } // END of success-authentications definition.

            leaf failed-connections  {
                type  yang:counter32;
                description "RADIUS Server count for connection failures";
            } // END of failed-connections definition.

        } // END of counters-container definition.
    } // END of radius-counters-state definition.
    grouping radius-debug-config {
        description
            "Configuration data related to debugging";
        leaf enable-debugging  {
            type  empty;
            description "This attribute is to enable/disable RADIUS debug logging";
        } // END of enable-debugging definition.

    } // END of radius-debug-config definition.
    grouping radius-debug-state {
        description
            "State data related to RADIUS debugging status";
        leaf terminal-debug-status  {
            type  cml-data-types:cml_on_off_t;
            description "Use this attribute to display RADIUS terminal debugging information.";
        } // END of terminal-debug-status definition.

    } // END of radius-debug-state definition.
    grouping radius-server-state {
        description
            "State data related to RADIUS Server status";
        leaf last-successful-authentication-time  {
            type  yang:date-and-time {
                pattern "\\d{4}-\\d{2}-\\d{2}T\\d{2}:\\d{2}:\\d{2}(\\.\\d+)?(Z|[\\+\\-]\\d{2}:\\d{2})";
                }
                description "RADIUS Server last successfull connection time";
            } // END of last-successful-authentication-time definition.

    } // END of radius-server-state definition.

    grouping  radius-grouping {
    description
        "Top level container for RADIUS configuration and operational data";
    container radius {
        description
            "Top level container for RADIUS configuration and operational data";
        container vrfs {
            description
                "This container defines RADIUS server vrf informations";

            list vrf {
                if-feature feature-list:HAVE_AAA;
                key "vrf-name";
                description
                    "Global RADIUS Configuration";
                leaf vrf-name  {
                    type  leafref {
                        path  "../config/vrf-name";
                    }
                    description "VRF Name associated with this instance";
                } // END of vrf-name definition.

                container config {
                    description
                        "radius related operation";
                    uses radius-global-config;
                } // END of config-container definition.
                container state {
                    config false;
                    description
                        "This container defines the RADIUS Global states.";
                    uses radius-global-config;
                } // END of state-container definition.
                container remote-servers {
                    description
                        "This container defines RADIUS Server informations";

                    list server {
                    when " /ipi-radius:radius/ipi-radius:vrfs/ipi-radius:vrf/ipi-radius:remote-servers/ipi-radius:server/ipi-radius:config/ipi-radius:sequence-number ";
                        if-feature feature-list:HAVE_AAA;
                        key "host-address";
                        description
                            "This objectlist defines the RADIUS Server list";
                        leaf host-address  {
                            type  leafref {
                                path  "../config/host-address";
                            }
                            description "Use this attribute to set the RADIUS server hostname or IP address";
                        } // END of host-address definition.

                        container config {
                            description
                                "This container defines RADIUS server operation";
                            uses radius-server-config;
                        } // END of config-container definition.
                        container state {
                            config false;
                            description
                                "This container defines TACACS Server state intormation.";
                            uses radius-server-config;
                            uses radius-counters-state;
                            uses radius-server-state;
                        } // END of state-container definition.
                    } // End of server-list
                } // END of remote-servers-container definition.
            } // End of vrf-list
        } // END of vrfs-container definition.
        container debug {
            description
                "RADIUS debug Information";
            container config {
                description
                    "This container defines RADIUS Debug Configuration";
                uses radius-debug-config;
            } // END of config-container definition.
            container state {
                config false;
                description
                    "This container defines RADIUS Debug state";
                uses radius-debug-config;
                uses radius-debug-state;
            } // END of state-container definition.
        } // END of debug-container definition.
    } // END of radius-container definition.
    } // END of radius-grouping definition.

    uses radius-grouping;

    rpc radius-clear-all-server-counters {
        description "Use this RPC to clear counters for all RADIUS servers";
        input  {
            leaf vrf-name  {
                type string;
                mandatory true;
                description "VRF Name associated with this instance";
            }
        }
    }

    rpc radius-clear-server-counters {
        description "Use this RPC to clear counters for a RADIUS server by hostname or IP
                    address";
        input  {
            leaf hostname  {
                type cml-data-types:cml_hostpname_t;
                mandatory true;
                description "Use this attribute to set the RADIUS server host name or IP address";
            }
            leaf vrf-name  {
                type string;
                mandatory true;
                description "VRF Name associated with this instance";
            }
        }
    }

    rpc radius-terminal-debug-on {
        description "Use this RPC to turn on RADIUS terminal debug logs";
    }

    rpc radius-terminal-debug-off {
        description "Use this RPC to turn off RADIUS terminal debug logs";
    }

}

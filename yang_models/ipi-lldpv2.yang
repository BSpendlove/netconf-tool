/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-lldpv2.yang
*
*/

module ipi-lldpv2 {

    yang-version 1.1;

    namespace   "http://www.ipinfusion.com/yang/ocnos/ipi-lldpv2";

    prefix "ipi-lldpv2";

    import cml-data-types {
        prefix cml-data-types;
        revision-date 2022-04-04;
    }

    import ipi-lldp-types {
        prefix ipi-lldp-types;
        revision-date 2022-01-12;
    }

    import ipi-interface {
        prefix ipi-interface;
        revision-date 2022-04-05;
    }

    import ietf-yang-types {
        prefix yang;
        revision-date 2013-07-15;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "Link Layer Discovery Protocol";


    revision "2022-03-28" {
        description "Updated data type from bool to empty for LLDP Global TLV options enable attributes";
        reference " 0.5.1.";
    }

    revision "2022-01-12" {
        description "Added if-feature for submodule";
        reference " 0.5.0.";
    }

    revision "2021-08-03" {
        description "New attribute disable-lldp-agent added to exclude interface when LLDP enabled globally";
        reference " 0.4.0.";
    }

    revision "2021-03-09" {
        description "Changed the type of descripition attribute to CML_RAW_STRING_T";
        reference " 0.3.0.";
    }

    revision "2020-12-15" {
        description "Change to have data-types in lower case instead of camel case";
        reference " 0.3.0.";
    }

    revision "2020-11-13" {
        description "Exec mode lldp commands changed as RPCs   Openconfig Yang model: https://github.com/openconfig/public/blob/master/release/models/lldp/openconfig-lldp.yang";
        reference " 0.2.0.";
    }

    revision "2020-07-15" {
        description "Initial Version";
        reference " 0.1.0.";
    }

    grouping lldp-global-custom-tlv-top {
        description
            "LLDP custom TLVs top level group";
        container global-tlv-control {
            description
                "Enclosing container configuration and state data for global TLV";
            uses global-basic-management-top;
            uses global-ieee-8021-org-specific-top;
            uses global-ieee-8023-org-specific-top;
        } // END of global-tlv-control-container definition.
    } // END of lldp-global-custom-tlv-top definition.
    grouping global-ieee-8021-org-specific-top {
        description
            "LLDP ieee 8021 informationi top level group";
        container global-ieee-8021-org-specific {
            description
                "Enclosing container for LLDP ieee 8021 configuration";
            container config {
                description
                    "LLDP ieee8021 specific configuration data on each interface";
                uses lldp-global-ieee-8021-org-specific-config;
            } // END of config-container definition.
            container state {
                config false;
                description
                    "Operational state data";
                uses lldp-global-ieee-8021-org-specific-config;
            } // END of state-container definition.
        } // END of global-ieee-8021-org-specific-container definition.
    } // END of global-ieee-8021-org-specific-top definition.
    grouping global-ieee-8023-org-specific-top {
        description
            "LLDP ieee 8023 specific group";
        container global-ieee-8023-org-specific {
            description
                "Enclosing container for LLDP ieee 8023 specification";
            container config {
                description
                    "LLDP ieee 8023 specific configuration data";
                uses lldp-global-ieee-8023-org-specific-config;
            } // END of config-container definition.
            container state {
                config false;
                description
                    "LLDP ieee 8023 specific operational state data";
                uses lldp-global-ieee-8023-org-specific-config;
            } // END of state-container definition.
        } // END of global-ieee-8023-org-specific-container definition.
    } // END of global-ieee-8023-org-specific-top definition.
    grouping global-basic-management-top {
        description
            "LLDP agent basic management top level group";
        container global-basic-management {
            description
                "Enclosing container for configuration and state data for LLDP agent
                        basic management";
            container config {
                description
                    "Configuration data for LLDP agent basic management on each interface";
                uses lldp-global-basic-management-config;
            } // END of config-container definition.
            container state {
                config false;
                description
                    "Operational state data";
                uses lldp-global-basic-management-config;
            } // END of state-container definition.
        } // END of global-basic-management-container definition.
    } // END of global-basic-management-top definition.
    grouping lldp-global-basic-management-config {
        description
            "LLDP agent basic management group";
        leaf port-description  {
            type  empty;
            description "This attribute specifies to include basic management port description
                        information in LLDP TLV";
        } // END of port-description definition.

        leaf system-description  {
            type  empty;
            description "This attribute specifies to include basic management system
                        description information in LLDP TLV";
        } // END of system-description definition.

        leaf system-name  {
            type  empty;
            description "This attribute specifies to include basic management system name
                        information in LLDP TLV";
        } // END of system-name definition.

        leaf system-capabilities  {
            type  empty;
            description "This attribute specifies to include basic management system
                        capabilities information in LLDP TLV";
        } // END of system-capabilities definition.

        leaf management-address  {
            type  empty;
            description "This attribute specifies to include basic management
                        management-address information in LLDP TLV";
        } // END of management-address definition.

    } // END of lldp-global-basic-management-config definition.
    grouping lldp-global-ieee-8023-org-specific-config {
        description
            "LLDP ieee 8023 specific data attributes group";
        leaf mac-phy  {
            type  empty;
            description "This attribute specifies to include ieee-8023-org-specific MAC or PHY
                        information in LLDP TLV";
        } // END of mac-phy definition.

        leaf max-mtu-size  {
            type  empty;
            description "This attribute specifies to include ieee-8023-org-specific maximum mtu
                        size information in LLDP TLV";
        } // END of max-mtu-size definition.

        leaf power-via-mdi  {
            if-feature feature-list:HAVE_POE;
            type  empty;
            description "This attribute specifies to include ieee-8023-org-specific power via
                        mdi information in LLDP TLV";
        } // END of power-via-mdi definition.

    } // END of lldp-global-ieee-8023-org-specific-config definition.
    grouping lldp-global-ieee-8021-org-specific-config {
        description
            "LLDP ieee 8021 specific configuration attributes group";
        leaf port-vlan-id  {
            type  empty;
            description "This attribute specifies to include ieee-8021-org-specific port
                        vlan-id information in LLDP TLV";
        } // END of port-vlan-id definition.

        leaf port-protocol-vlan-id  {
            type  empty;
            description "This attribute specifies to include ieee-8021-org-specific port
                        protocol vlan-id information in LLDP TLV";
        } // END of port-protocol-vlan-id definition.

        leaf vlan-name  {
            type  empty;
            description "This attribute specifies to include ieee-8021-org-specific vlan name
                        information in LLDP TLV";
        } // END of vlan-name definition.

        leaf protocol-identifier  {
            type  empty;
            description "This attribute specifies to include ieee-8021-org-specific protocol
                        identifier information in LLDP TLV";
        } // END of protocol-identifier definition.

        leaf vid-digest  {
            type  empty;
            description "This attribute specifies to include ieee-8021-org-specific vid usage
                        digest information in LLDP TLV";
        } // END of vid-digest definition.

        leaf management-vlan-id  {
            type  empty;
            description "This attribute specifies to include ieee-8021-org-specific management
                        vlan-id information in LLDP TLV";
        } // END of management-vlan-id definition.

        leaf link-aggregation  {
            type  empty;
            description "This attribute specifies to include ieee-8021-org-specific link
                        aggregation information in LLDP TLV";
        } // END of link-aggregation definition.

        leaf dcb-exchange  {
            if-feature feature-list:HAVE_DCB;
            type  empty;
            description "This attribute specifies to include ieee-8021-org-specific data center
                        bridging information in LLDP TLV";
        } // END of dcb-exchange definition.

    } // END of lldp-global-ieee-8021-org-specific-config definition.
    grouping lldp-global-config {
        description
            "LLDP global configuration data attributes group";
        leaf enable  {
            type  empty;
            description "Enable or disable the LLDP protocol at node level";
        } // END of enable definition.

        leaf notification-interval  {
            if-feature feature-list:HAVE_SNMP;
            type  uint16 {
                 range "5..3600"  {
                    description "5..3600:lldp notification interval value in seconds";
                 }
            }
            default "30";
            description "This object controls the interval between transmission of
                        LLDP notifications during normal transmission periods";
        } // END of notification-interval definition.

    } // END of lldp-global-config definition.
    grouping lldp-global-state {
        description
            "LLDP global operational state attributes group";
        leaf system-capabilities-enabled  {
            type  cml-data-types:cml_line_t {
                length "1..1965";
            }
            description "Enabled system capabilities";
        } // END of system-capabilities-enabled definition.

        leaf host-name-information  {
            type  string {
                length "1..1965";
                pattern "[^?' =,>|]+";
            }
            description "Hostname information for LLDP";
        } // END of host-name-information definition.

    } // END of lldp-global-state definition.
    grouping lldp-global-counters {
        description
            "LLDP global level counters group";
        container counters {
            config false;
            description
                "Enclosing container for lldp global level counter";
            leaf remote-inserts  {
                type  yang:counter32;
                description "Counter for number of times complete set of information
                            advertised by a particular MSAP has been inserted into tables";
            } // END of remote-inserts definition.

            leaf remote-deletes  {
                type  yang:counter32;
                description "Counter for numer of times the complete set of information
                            advertised by a particular MSAP has been deleted from
                            tables.";
            } // END of remote-deletes definition.

            leaf remote-drops  {
                type  yang:counter32;
                description "Counter for number of times complete set of information
                            advertised by a particular MSAP could not be entered
                            into tables";
            } // END of remote-drops definition.

            leaf remote-ageouts  {
                type  yang:counter32;
                description "Counter for number of times the complete set of information
                            advertised by a particular MSAP could not be entered
                            into tables";
            } // END of remote-ageouts definition.

        } // END of counters-container definition.
    } // END of lldp-global-counters definition.
    grouping lldp-ieee-8023-org-specific-interface-config {
        description
            "LLDP ieee 8023 specific data attributes group";
        leaf mac-phy  {
            type  ipi-lldp-types:lldp_tlv_select_type;
            default "not-set";
            description "This attribute specifies to include ieee-8023-org-specific MAC or PHY
                        information in LLDP TLV";
        } // END of mac-phy definition.

        leaf max-mtu-size  {
            type  ipi-lldp-types:lldp_tlv_select_type;
            default "not-set";
            description "This attribute specifies to include ieee-8023-org-specific maximum mtu
                        size information in LLDP TLV";
        } // END of max-mtu-size definition.

        leaf power-via-mdi  {
            if-feature feature-list:HAVE_POE;
            type  ipi-lldp-types:lldp_tlv_select_type;
            default "not-set";
            description "This attribute specifies to include ieee-8023-org-specific power via
                        mdi information in LLDP TLV";
        } // END of power-via-mdi definition.

    } // END of lldp-ieee-8023-org-specific-interface-config definition.
    grouping lldp-management-if-config {
        description
            "LLDP management identifier configuration configuration data group";
        leaf locally-assigned-chassis-id  {
            type  string {
                length "1..1965";
                pattern "[^?' =,>|]+";
            }
            default "NULL";
            description "This attribute used to identify the chassis component associated with
                        the local system";
        } // END of locally-assigned-chassis-id definition.

    } // END of lldp-management-if-config definition.
    grouping lldp-management-if-top {
        description
            "LLDP management identifier group";
        container management-if {
            description
                "Enclosing container for management identifier";
            container config {
                description
                    "LLDP management identifier configuration data";
                uses lldp-management-if-config;
            } // END of config-container definition.
            container state {
                config false;
                description
                    "LLPD management identifier opertaional state data";
                uses lldp-management-if-config;
            } // END of state-container definition.
        } // END of management-if-container definition.
    } // END of lldp-management-if-top definition.
    grouping ieee-8023-org-specific-top {
        description
            "LLDP ieee 8023 specific group";
        container ieee-8023-org-specific {
            description
                "Enclosing container for LLDP ieee 8023 specification";
            container config {
                description
                    "LLDP ieee 8023 specific configuration data";
                uses lldp-ieee-8023-org-specific-interface-config;
            } // END of config-container definition.
            container state {
                config false;
                description
                    "LLDP ieee 8023 specific operational state data";
                uses lldp-ieee-8023-org-specific-interface-config;
            } // END of state-container definition.
        } // END of ieee-8023-org-specific-container definition.
    } // END of ieee-8023-org-specific-top definition.
    grouping lldp-ieee-8021-org-specific-interface-config {
        description
            "LLDP ieee 8021 specific configuration attributes group";
        leaf port-vlan-id  {
            type  ipi-lldp-types:lldp_tlv_select_type;
            default "not-set";
            description "This attribute specifies to include ieee-8021-org-specific port
                        vlan-id information in LLDP TLV";
        } // END of port-vlan-id definition.

        leaf port-protocol-vlan-id  {
            type  ipi-lldp-types:lldp_tlv_select_type;
            default "not-set";
            description "This attribute specifies to include ieee-8021-org-specific port
                        protocol vlan-id information in LLDP TLV";
        } // END of port-protocol-vlan-id definition.

        leaf vlan-name  {
            type  ipi-lldp-types:lldp_tlv_select_type;
            default "not-set";
            description "This attribute specifies to include ieee-8021-org-specific vlan name
                        information in LLDP TLV";
        } // END of vlan-name definition.

        leaf protocol-identifier  {
            type  ipi-lldp-types:lldp_tlv_select_type;
            default "not-set";
            description "This attribute specifies to include ieee-8021-org-specific protocol
                        identifier information in LLDP TLV";
        } // END of protocol-identifier definition.

        leaf vid-digest  {
            type  ipi-lldp-types:lldp_tlv_select_type;
            default "not-set";
            description "This attribute specifies to include ieee-8021-org-specific vid usage
                        digest information in LLDP TLV";
        } // END of vid-digest definition.

        leaf management-vlan-id  {
            type  ipi-lldp-types:lldp_tlv_select_type;
            default "not-set";
            description "This attribute specifies to include ieee-8021-org-specific management
                        vlan-id information in LLDP TLV";
        } // END of management-vlan-id definition.

        leaf link-aggregation  {
            type  ipi-lldp-types:lldp_tlv_select_type;
            default "not-set";
            description "This attribute specifies to include ieee-8021-org-specific link
                        aggregation information in LLDP TLV";
        } // END of link-aggregation definition.

        leaf dcb-exchange  {
            if-feature feature-list:HAVE_DCB;
            type  ipi-lldp-types:lldp_tlv_select_type;
            default "not-set";
            description "This attribute specifies to include ieee-8021-org-specific data center
                        bridging information in LLDP TLV";
        } // END of dcb-exchange definition.

    } // END of lldp-ieee-8021-org-specific-interface-config definition.
    grouping ieee-8021-org-specific-top {
        description
            "LLDP ieee 8021 informationi top level group";
        container ieee-8021-org-specific {
            description
                "Enclosing container for LLDP ieee 8021 configuration";
            container config {
                description
                    "LLDP ieee8021 specific configuration data on each interface";
                uses lldp-ieee-8021-org-specific-interface-config;
            } // END of config-container definition.
            container state {
                config false;
                description
                    "Operational state data";
                uses lldp-ieee-8021-org-specific-interface-config;
            } // END of state-container definition.
        } // END of ieee-8021-org-specific-container definition.
    } // END of ieee-8021-org-specific-top definition.
    grouping lldp-basic-management-interface-config {
        description
            "LLDP agent basic management group";
        leaf port-description  {
            type  ipi-lldp-types:lldp_tlv_select_type;
            default "not-set";
            description "This attribute specifies to include basic management port description
                        information in LLDP TLV";
        } // END of port-description definition.

        leaf system-description  {
            type  ipi-lldp-types:lldp_tlv_select_type;
            default "not-set";
            description "This attribute specifies to include basic management system
                        description information in LLDP TLV";
        } // END of system-description definition.

        leaf system-name  {
            type  ipi-lldp-types:lldp_tlv_select_type;
            default "not-set";
            description "This attribute specifies to include basic management system name
                        information in LLDP TLV";
        } // END of system-name definition.

        leaf system-capabilities  {
            type  ipi-lldp-types:lldp_tlv_select_type;
            default "not-set";
            description "This attribute specifies to include basic management system
                        capabilities information in LLDP TLV";
        } // END of system-capabilities definition.

        leaf management-address  {
            type  ipi-lldp-types:lldp_tlv_select_type;
            default "not-set";
            description "This attribute specifies to include basic management
                        management-address information in LLDP TLV";
        } // END of management-address definition.

    } // END of lldp-basic-management-interface-config definition.
    grouping basic-management-top {
        description
            "LLDP agent basic management top level group";
        container basic-management {
            description
                "Enclosing container for configuration and state data for LLDP agent
                        basic management";
            container config {
                description
                    "Configuration data for LLDP agent basic management on each interface";
                uses lldp-basic-management-interface-config;
            } // END of config-container definition.
            container state {
                config false;
                description
                    "Operational state data";
                uses lldp-basic-management-interface-config;
            } // END of state-container definition.
        } // END of basic-management-container definition.
    } // END of basic-management-top definition.
    grouping lldp-custom-tlv-top {
        description
            "LLDP custom TLVs top level group";
        container tlv-control {
            description
                "Enclosing container configuration and state data for TLV";
            uses basic-management-top;
            uses ieee-8021-org-specific-top;
            uses ieee-8023-org-specific-top;
            uses med-capabilities-top;
        } // END of tlv-control-container definition.
    } // END of lldp-custom-tlv-top definition.
    grouping lldp-global-top {
        description
            "LLDP global level information grouping";
        container global {
            description
                "LLDP global level information";
            container config {
                description
                    "Configuration data for LLDP global level";
                uses lldp-global-config;
            } // END of config-container definition.
            container state {
                config false;
                description
                    "Operation state data for LLDP global level";
                uses lldp-global-config;
                uses lldp-global-state;
                uses lldp-global-counters;
            } // END of state-container definition.
            uses lldp-global-custom-tlv-top;
            uses lldp-management-if-top;
        } // END of global-container definition.
    } // END of lldp-global-top definition.
    grouping lldp-v2-agent-tlv-config {
        description
            "LLDP Agent TLV group";
        leaf port-address  {
            type  ipi-lldp-types:lldp_mgmt_addr_t;
            default "mac-address";
            description "This attribute specifies sub type of the Management Address TLV. Can
                        be configured as mac-addresss or ip-address";
        } // END of port-address definition.

        leaf chassis-id  {
            type  ipi-lldp-types:lldp_chassis_t;
            default "mac-address";
            description "This attribute specifies chassis ID subtype for the LLDP agent on a
                        port. Can be configured as if-alias or ip-address or mac-address or
                        if-name or locally-assgined name";
        } // END of chassis-id definition.

        leaf port-id  {
            type  ipi-lldp-types:lldp_port_t;
            default "mac-address";
            description "This attribute specifies sub type of the port id TLV. Can be
                        configured as if-alias or mac-address or ip-address or if-name or
                        agent-circuit-id or locally assigned name";
        } // END of port-id definition.

    } // END of lldp-v2-agent-tlv-config definition.
    grouping lldp-v2-agent-tlv-media-capabilities-config {
        description
            "LLDP agent TLV media selection top level group";
        leaf network-policy  {
            type  ipi-lldp-types:lldp_tlv_select_type;
            default "not-set";
            description "Network policy information configured on the port for connected media
                        endpoint. Following network policy
                        will be supported VLAN ID, Priority Tagging, VLAN DSCP";
        } // END of network-policy definition.

        leaf location  {
            type  ipi-lldp-types:lldp_tlv_select_type;
            default "not-set";
            description "Media Tlv type Location information configured for the port";
        } // END of location definition.

        leaf inventory  {
            type  ipi-lldp-types:lldp_tlv_select_type;
            default "not-set";
            description "Includes the TLV for information like hardware revision, software
                        revision etc based on the current hardware platform and the
                        software version";
        } // END of inventory definition.

        leaf media-capabilities  {
            type  ipi-lldp-types:lldp_tlv_select_type;
            default "not-set";
            description "Includes various media-capabilties of the box for the neighbor";
        } // END of media-capabilities definition.

        leaf extended-power-via-mdi  {
            if-feature feature-list:HAVE_POE;
            type  ipi-lldp-types:lldp_tlv_select_type;
            default "not-set";
            description "For PoE-capable devices, this TLV includes Power Type Field, Power
                        Source Field, Priority field etc";
        } // END of extended-power-via-mdi definition.

    } // END of lldp-v2-agent-tlv-media-capabilities-config definition.
    grouping med-capabilities-top {
        description
            "LLDP agent TLV media capabilities top level group";
        container tlv-media-capabilities {
            description
                "Enclosing container for configuration and state data for
                        LLDP tlv media capabilities";
            container config {
                description
                    "Configuration data for tlv media capability on agent type";
                uses lldp-v2-agent-tlv-media-capabilities-config;
            } // END of config-container definition.
            container state {
                config false;
                description
                    "Operational state data for LLDP agent media capabilities on each
                            interface";
                uses lldp-v2-agent-tlv-media-capabilities-config;
            } // END of state-container definition.
        } // END of tlv-media-capabilities-container definition.
    } // END of med-capabilities-top definition.
    grouping lldp-v2-agent-tlv-top {
        description
            "LLDP agent TLV top level group";
        container agent-tlv {
            description
                "Enclosing container for configuration and state data LLDP Agent TLV";
            container config {
                description
                    "Configuration data for LLDP agent TLV on each interface";
                uses lldp-v2-agent-tlv-config;
            } // END of config-container definition.
            container state {
                config false;
                description
                    "Operational state data";
                uses lldp-v2-agent-tlv-config;
            } // END of state-container definition.
        } // END of agent-tlv-container definition.
    } // END of lldp-v2-agent-tlv-top definition.
    grouping lldp-v2-receive-config {
        description
            "LLDP receive configuration attributes group";
        leaf neighbor-limit  {
            when " /ipi-lldpv2:lldp/ipi-lldpv2:interfaces/ipi-lldpv2:interface/ipi-lldpv2:agent/ipi-lldpv2:receive/ipi-lldpv2:config/ipi-lldpv2:neighbor-timer  or /ipi-lldpv2:lldp/ipi-lldpv2:interfaces/ipi-lldpv2:interface/ipi-lldpv2:agent/ipi-lldpv2:receive/ipi-lldpv2:config/ipi-lldpv2:port-timer ";
            type  uint32 {
                 range "1..65535"  {
                    description "1..65535:Set the limit";
                 }
            }
            description "This attribute configures limit for remote table entries to take
                        action to discard or delete entries";
        } // END of neighbor-limit definition.

        leaf neighbor-timer  {
            when " /ipi-lldpv2:lldp/ipi-lldpv2:interfaces/ipi-lldpv2:interface/ipi-lldpv2:agent/ipi-lldpv2:receive/ipi-lldpv2:config/ipi-lldpv2:neighbor-limit + not(/ipi-lldpv2:lldp/ipi-lldpv2:interfaces/ipi-lldpv2:interface/ipi-lldpv2:agent/ipi-lldpv2:receive/ipi-lldpv2:config/ipi-lldpv2:port-timer) + not(/ipi-lldpv2:lldp/ipi-lldpv2:interfaces/ipi-lldpv2:interface/ipi-lldpv2:agent/ipi-lldpv2:receive/ipi-lldpv2:config/ipi-lldpv2:port-mac) ";
            type  uint32 {
                 range "1..65535"  {
                    description "1..65535:set the Timer";
                 }
            }
            description "This attribute configures timer to discard received message when
                        remote table is full";
        } // END of neighbor-timer definition.

        leaf port-mac  {
            when " /ipi-lldpv2:lldp/ipi-lldpv2:interfaces/ipi-lldpv2:interface/ipi-lldpv2:agent/ipi-lldpv2:receive/ipi-lldpv2:config/ipi-lldpv2:neighbor-limit + /ipi-lldpv2:lldp/ipi-lldpv2:interfaces/ipi-lldpv2:interface/ipi-lldpv2:agent/ipi-lldpv2:receive/ipi-lldpv2:config/ipi-lldpv2:port-timer + not(/ipi-lldpv2:lldp/ipi-lldpv2:interfaces/ipi-lldpv2:interface/ipi-lldpv2:agent/ipi-lldpv2:receive/ipi-lldpv2:config/ipi-lldpv2:neighbor-timer) ";
            type  cml-data-types:cml_mac_addr_t {
                length "1..1965";
            }
            description "This attribute uses given port MAC to take action when the remote
                        table is full";
        } // END of port-mac definition.

        leaf port-timer  {
            when " /ipi-lldpv2:lldp/ipi-lldpv2:interfaces/ipi-lldpv2:interface/ipi-lldpv2:agent/ipi-lldpv2:receive/ipi-lldpv2:config/ipi-lldpv2:neighbor-limit + /ipi-lldpv2:lldp/ipi-lldpv2:interfaces/ipi-lldpv2:interface/ipi-lldpv2:agent/ipi-lldpv2:receive/ipi-lldpv2:config/ipi-lldpv2:port-mac + not(/ipi-lldpv2:lldp/ipi-lldpv2:interfaces/ipi-lldpv2:interface/ipi-lldpv2:agent/ipi-lldpv2:receive/ipi-lldpv2:config/ipi-lldpv2:neighbor-timer) ";
            type  uint32 {
                 range "1..65535"  {
                    description "1..65535:set the Timer";
                 }
            }
            description "This attribute configures timer to discard or delete existing info for
                        received message port MAC when the remote table is full";
        } // END of port-timer definition.

    } // END of lldp-v2-receive-config definition.
    grouping remote-vlan-info {
        description
            "remote vlan information operationl state group";
        leaf vlan-id  {
            type  uint16;
            description "The integer value used to identify the port's VLAN
                        identifier associated with the remote system.
                        If the remote system either does not know the PVID or does not support
                        port-based VLAN operation, the value of
                        this attribute could be 0.";
        } // END of vlan-id definition.

        leaf vlan-name  {
            type  string {
                length "1..1965";
                pattern "[^?' =,>|]+";
            }
            description "The string used to identify the port's configured vlan name with
                        remote system";
        } // END of vlan-name definition.

    } // END of remote-vlan-info definition.
    grouping vlan-list {
        description
            "LLDP vlan list information operational state group";

        list vlan-list {
            key "vlan-id";
            config false;
            description
                "Object list for vlan-list operational state";
            uses remote-vlan-info;
        } // End of vlan-list-list
    } // END of vlan-list definition.
    grouping remote-management-info {
        description
            "LLDP remote mangement information operational data group";
        leaf address  {
            type  string {
                length "1..1965";
                pattern "[^?' =,>|]+";
            }
            description "The value of Remote management ip/mac/unknown address";
        } // END of address definition.

        leaf address-sub-type  {
            type  cml-data-types:cml_line_t {
                length "1..1965";
            }
            description "Remote management address type";
        } // END of address-sub-type definition.

        leaf interface-number-sub-type  {
            type  string {
                length "1..1965";
                pattern "[^?' =,>|]+";
            }
            description "Remote interface number sub type";
        } // END of interface-number-sub-type definition.

        leaf interface-number  {
            type  uint32;
            description "Remote interface number";
        } // END of interface-number definition.

        leaf oid  {
            type  string {
                length "1..1965";
                pattern "[^?' =,>|]+";
            }
            description "Remote OID number";
        } // END of oid definition.

    } // END of remote-management-info definition.
    grouping management-list {
        description
            "Neighbor management information group";

        list management-list {
            key "address";
            config false;
            description
                "Object list for neighbor management information";
            uses remote-management-info;
        } // End of management-list-list
    } // END of management-list definition.
    grouping neighbor-state {
        description
            "LLDP neighbors operational data attributes group";
        leaf mac-address  {
            type  cml-data-types:cml_mac_addr_t {
                length "1..1965";
            }
            description "Remote system MAC address";
        } // END of mac-address definition.

        leaf system-name  {
            type  string {
                length "1..1965";
            }
            description "Remote system name";
        } // END of system-name definition.

        leaf chassis-component  {
            type  string {
                length "1..1965";
            }
            description "Remote chassis component";
        } // END of chassis-component definition.

        leaf chassis-id-type  {
            type  uint8;
            description "Remote chassis type";
        } // END of chassis-id-type definition.

        leaf port-component  {
            type  string {
                length "1..1965";
            }
            description "Remote port component";
        } // END of port-component definition.

        leaf port-id  {
            type  string {
                length "1..1965";
            }
            description "Remote port id";
        } // END of port-id definition.

        leaf port-description  {
            type  string {
                length "1..1965";
            }
            description "Remote port description";
        } // END of port-description definition.

        leaf port-sub-type  {
            type  uint16;
            description "Remote port sub type";
        } // END of port-sub-type definition.

        leaf interface-alias  {
            type  string {
                length "1..1965";
            }
            description "Remote interface alias name";
        } // END of interface-alias definition.

        leaf interface-agent-circuit-id  {
            type  string {
                length "1..1965";
            }
            description "Remote interface agent circuit identifier";
        } // END of interface-agent-circuit-id definition.

        leaf ttl  {
            type  uint16;
            description "Remote time to live value";
        } // END of ttl definition.

        leaf interface-number  {
            type  uint32;
            description "Remote interface number";
        } // END of interface-number definition.

        leaf interface-number-sub-type  {
            type  string {
                length "1..1965";
                pattern "[^?' =,>|]+";
            }
            description "Remote interface number sub type";
        } // END of interface-number-sub-type definition.

        leaf port-vlan-id  {
            type  uint16;
            description "Remote interface vlan identifier";
        } // END of port-vlan-id definition.

        leaf pp-vlanid  {
            type  uint16;
            description "Remote interface protocol port vlan identifier";
        } // END of pp-vlanid definition.

        leaf protocol  {
            type  ipi-lldp-types:lldp_protoid_t;
            description "Advertised remote protocols";
        } // END of protocol definition.

        leaf vid-usage-digest  {
            type  uint32;
            description "Remote VID Usage Digest value";
        } // END of vid-usage-digest definition.

        leaf management-vlan  {
            type  uint16;
            description "Remote Management Vlan identifier";
        } // END of management-vlan definition.

        leaf auto-negotiation-support  {
            type  uint8;
            description "Remote interface auto negotiation support availability,
                        0-Not-supported, 1-Supported, 3-Supported and Enabled";
        } // END of auto-negotiation-support definition.

        leaf auto-negotiation-capability  {
            type  uint16;
            description "Remote interface auto negotiation capability";
        } // END of auto-negotiation-capability definition.

        leaf operational-mau-type  {
            type  uint16;
            description "Remote Operational MAU Type";
        } // END of operational-mau-type definition.

        leaf link-aggregate-capability  {
            type  cml-data-types:cml_line_t {
                length "1..1965";
            }
            description "Remote interface aggregation capability support";
        } // END of link-aggregate-capability definition.

        leaf link-aggregate-id  {
            type  uint32;
            description "Remote link Aggregation ID";
        } // END of link-aggregate-id definition.

        leaf max-frame-size  {
            type  uint16;
            description "Remote maximum Frame Size";
        } // END of max-frame-size definition.

        leaf system-description  {
            type  string {
                length "1..1965";
            }
            description "Remote system description";
        } // END of system-description definition.

        leaf system-capabilties  {
            type  cml-data-types:cml_line_t {
                length "1..1965";
            }
            description "Remote supported system capabilties";
        } // END of system-capabilties definition.

        leaf system-capabilties-enabled  {
            type  cml-data-types:cml_line_t {
                length "1..1965";
            }
            description "Remote system enabled capabilties";
        } // END of system-capabilties-enabled definition.

        leaf mdi-power-support  {
            if-feature feature-list:HAVE_POE;
            type  uint8;
            description "Remote mdi power over ethernet support information";
        } // END of mdi-power-support definition.

        leaf poe-power-class  {
            if-feature feature-list:HAVE_POE;
            type  uint8;
            description "Remote mdi power over ethernet class";
        } // END of poe-power-class definition.

        leaf pse-power-pair  {
            if-feature feature-list:HAVE_POE;
            type  uint8;
            description "Remote power sourcing equipment";
        } // END of pse-power-pair definition.

        leaf type-source-priority  {
            if-feature feature-list:HAVE_POE;
            type  uint8;
            description "Remote Bit map value of type/source/priority";
        } // END of type-source-priority definition.

        leaf pd-requested-power  {
            if-feature feature-list:HAVE_POE;
            type  uint16;
            description "Remote powered device requested power value";
        } // END of pd-requested-power definition.

        leaf pse-allocated-power  {
            if-feature feature-list:HAVE_POE;
            type  uint16;
            description "Remote power sourcing equipment allocated power value";
        } // END of pse-allocated-power definition.

    } // END of neighbor-state definition.
    grouping neighbor-top {
        description
            "LLDP neighbors operational data top level group";

        list neighbor {
            key "mac-address";
            config false;
            description
                "List of LLDP neighbors";
            leaf mac-address  {
                type  leafref {
                    path  "../state/mac-address";
                }
                description "Neighbor mac-address";
            } // END of mac-address definition.

            container state {
                config false;
                description
                    "Neighbors operational state data";
                uses neighbor-state;
                uses vlan-list;
                uses management-list;
            } // END of state-container definition.
        } // End of neighbor-list
    } // END of neighbor-top definition.
    grouping neighbors-agent-top {
        description
            "LLDP agent operational data top level group";

        list agent {
            key "agent-type";
            config false;
            description
                "List of interface Agents";
            leaf agent-type  {
                type  ipi-lldp-types:lldp_agent_t;
                description "LLDP agent type";
            } // END of agent-type definition.

            uses neighbor-top;
        } // End of agent-list
    } // END of neighbors-agent-top definition.
    grouping lldp-v2-receive-counters {
        description
            "LLDP receive counters";
        leaf frames-aged-out  {
            type  yang:counter32;
            description "The number of LLDP frames aged out on interface";
        } // END of frames-aged-out definition.

        leaf frames-discarded  {
            type  yang:counter32;
            description "The number of LLDP frames discarded on interface. This counter can
                        provide an indication that LLDP header formatting problems may exist
                        with the local LLDP agent in the sending system or that LLDPDU
                        validation problems may exist with the local LLDP agent in the
                        receiving system";
        } // END of frames-discarded definition.

        leaf frames-invalid  {
            type  yang:counter32;
            description "The number of invalid LLDP frames received by this LLDP agent on
                        interface";
        } // END of frames-invalid definition.

        leaf frames-valid  {
            type  yang:counter32;
            description "The number of valid LLDP frames received by this LLDP agent on
                        interface";
        } // END of frames-valid definition.

        leaf tlvs-discarded  {
            type  yang:counter32;
            description "The number of LLDP TLVs discarded for any reason by this LLDP agent on
                        interace";
        } // END of tlvs-discarded definition.

        leaf tlvs-unrecognized  {
            type  yang:counter32;
            description "The number of LLDP TLVs received on the given port that are not
                        recognized by this LLDP agent on interface. An unrecognized TLV is
                        referred to as the TLV whose type value is in the range of reserved
                        TLV types (000 1001 - 111 1110) in Table 9.1 of IEEE Std 802.1AB-2004.
                        An unrecognized TLV may be a basic management TLV from a later LLDP
                        version";
        } // END of tlvs-unrecognized definition.

    } // END of lldp-v2-receive-counters definition.
    grouping receive-top {
        description
            "LLDP receive information top level group";
        container receive {
            description
                "Enclosing container for configuration and state data for LLDP packet
                        reception";
            container config {
                description
                    "Configuration data for LLDP agent on each interface";
                uses lldp-v2-receive-config;
            } // END of config-container definition.
            container state {
                config false;
                description
                    "Operational state data";
                uses lldp-v2-receive-config;
                uses lldp-v2-receive-counters;
            } // END of state-container definition.
        } // END of receive-container definition.
    } // END of receive-top definition.
    grouping lldp-v2-transmit-config {
        description
            "LLDP transmission configuration group";
        leaf reinit-delay  {
            type  uint32 {
                 range "1..10"  {
                    description "1..10:Reinitialization Delay";
                 }
            }
            default "2";
            description "The minimum time interval an LLDP port waits before re-initializing an
                        LLDP transmission";
        } // END of reinit-delay definition.

        leaf message-tx-interval  {
            type  uint32 {
                 range "5..3600"  {
                    description "5..3600:Interval value";
                 }
            }
            default "30";
            description "The delay between successive LLDP frame transmissions during normal
                        transmission periods";
        } // END of message-tx-interval definition.

        leaf message-tx-hold-multiplier  {
            type  uint32 {
                 range "1..100"  {
                    description "1..100:Trasmit hold value";
                 }
            }
            default "4";
            description "Multiplier of message-tx-interval to determine the Time To Live (TTL)
                        that is carried in LLDP frames transmitted by the LLDP agent";
        } // END of message-tx-hold-multiplier definition.

        leaf message-fast-tx  {
            type  uint32 {
                 range "1..3600"  {
                    description "1..3600:Transmit interval value";
                 }
            }
            default "1";
            description "The interval at which LLDP frames are transmitted on behalf of LLDP
                        agent during fast transmission periods";
        } // END of message-fast-tx definition.

        leaf tx-credit-max  {
            type  uint32 {
                 range "1..10"  {
                    description "1..10:Tx-max-credit Value in range 1-10";
                 }
            }
            default "5";
            description "The maximum number of consecutive LLDPDUs that can be transmitted at
                        any time";
        } // END of tx-credit-max definition.

        leaf tx-fast-init  {
            type  uint32 {
                 range "1..8"  {
                    description "1..8:Number of LLDP frames in range 1-8";
                 }
            }
            default "4";
            description "The number of LLDPDUs to send during the fast transmission periods";
        } // END of tx-fast-init definition.

    } // END of lldp-v2-transmit-config definition.
    grouping lldp-v2-transmit-counters {
        description
            "LLDP transmit counters group";
        container counters {
            config false;
            description
                "Enclosing container for LLDP transmit counters";
            leaf frames-out  {
                type  yang:counter32;
                description "The number of LLDP frames transmitted by this LLDP agent on the
                            indicated port to the destination";
            } // END of frames-out definition.

        } // END of counters-container definition.
    } // END of lldp-v2-transmit-counters definition.
    grouping lldp-v2-transmit-state {
        description
            "LLDP transmit state  operational datai attributes group";
        leaf tx-ttl  {
            type  uint16;
            description "The time to live value used in message transmission based on
                        message-tx-interval and message-tx-hold-multiplier values";
        } // END of tx-ttl definition.

    } // END of lldp-v2-transmit-state definition.
    grouping transmit-top {
        description
            "LLDP transmit top level group";
        container transmit {
            description
                "Enclosing container for configuration and state data LLDP packet
                        transmission";
            container config {
                description
                    "Configuration data for LLDP agent on each interface";
                uses lldp-v2-transmit-config;
            } // END of config-container definition.
            container state {
                config false;
                description
                    "Operational state data";
                uses lldp-v2-transmit-config;
                uses lldp-v2-transmit-state;
                uses lldp-v2-transmit-counters;
            } // END of state-container definition.
        } // END of transmit-container definition.
    } // END of transmit-top definition.
    grouping lldp-v2-agent-config {
        description
            "LLDP Agent for interface attributes group";
        leaf agent-type  {
            type  ipi-lldp-types:lldp_agent_t;
            description "LLDP agent type on this interface";
        } // END of agent-type definition.

        leaf enable-tx-rx  {
            type  ipi-lldp-types:lldp_enable_t;
            default "rxonly";
            description "Enables interface with LLDP protocol and specifies to send and(or)
                        receive packets on interface";
        } // END of enable-tx-rx definition.

    } // END of lldp-v2-agent-config definition.
    grouping lldp-v2-agent-top {
        description
            "LLDP Agent on each interface top level group";

        list agent {
        when " not(/ipi-lldpv2:lldp/ipi-lldpv2:interfaces/ipi-lldpv2:interface/ipi-lldpv2:config/ipi-lldpv2:disable-lldp-agent ) or /ipi-lldpv2:lldp/ipi-lldpv2:interfaces/ipi-lldpv2:interface/ipi-lldpv2:agent/ipi-lldpv2:config/ipi-lldpv2:agent-type != '2' ";
            key "agent-type";
            description
                "Configuration and state information";
            leaf agent-type  {
                type  leafref {
                    path  "../config/agent-type";
                }
                description "LLDP agent type on this interface";
            } // END of agent-type definition.

            container config {
                description
                    "Configuration data for LLDP agent on each interface";
                uses lldp-v2-agent-config;
            } // END of config-container definition.
            container state {
                config false;
                description
                    "Operational state data";
                uses lldp-v2-agent-config;
            } // END of state-container definition.
            uses transmit-top;
            uses receive-top;
            uses lldp-v2-agent-tlv-top;
            uses lldp-custom-tlv-top;
        } // End of agent-list
    } // END of lldp-v2-agent-top definition.
    grouping lldp-v2-interface-config {
        description
            "Configuration data for LLDP-V2 on each interface";
        leaf name  {
            type  leafref {
                path  "/ipi-interface:interfaces/ipi-interface:interface/ipi-interface:name";
            }
            description "The interface name to configure the OSPF parameters.";
        } // END of name definition.

        leaf disable-lldp-agent  {
            when " /ipi-lldpv2:lldp/ipi-lldpv2:global/ipi-lldpv2:config/ipi-lldpv2:enable + /ipi-lldpv2:lldp/ipi-lldpv2:interfaces/ipi-lldpv2:interface/ipi-lldpv2:agent/ipi-lldpv2:agent-type != '2' ";
            type  empty;
            description "Use this attribute to disable LLDP on interface when it is enabled
                        globally";
        } // END of disable-lldp-agent definition.

        leaf agent-circuit-id  {
            type  string {
                length "1..1965";
                pattern "[^?' =,>|]+";
            }
            default "NULL";
            description "DHCP agent circuit ID association on interface";
        } // END of agent-circuit-id definition.

        leaf med-device-type  {
            type  ipi-lldp-types:lldp_meddev_t;
            description "LLDP-MED type of interface. Class-0 is not defined, Class-1 is for
                        generic endpoints and is applicable to all endpoints that require the
                        base LLDP discovery services. Class-2  is for media endpoints and it
                        includes endpoints that have IP media capabilities. Class-3 is for
                        communication endpoints i.e., devices acting as end user communication
                        applicances. Calss-4 is for Network Connectivity Device. Class 5-255
                        are Reserved";
        } // END of med-device-type definition.

        leaf local-name  {
            type  string {
                length "1..1965";
                pattern "[^?' =,>|]+";
            }
            description "Interface sub type with local name";
        } // END of local-name definition.

    } // END of lldp-v2-interface-config definition.
    grouping lldp-interface-top {
        description
            "Top level container for LLDP-V2 on each interface";
        container interfaces {
            description
                "Top level container for LLDP-V2 on each interface";

            list interface {
                key "name";
                description
                    "List of interfaces on which LLDP is enabled / available";
                leaf name  {
                    type  leafref {
                        path  "../config/name";
                    }
                    description "The textual name of the interface. The value of this object should be
                                the name of the interface as assigned by the local device and should
                                be suitable for use in commands entered at the device's `console'.
                                This might be a text name, such as `le0' or a simple port number, such
                                as `1', depending on the interface naming syntax of the device. If
                                several entries in the ifTable together represent a single interface
                                as named by the device, then each will have the same value of name.
                                Note that for an agent which responds to SNMP queries concerning an
                                interface on some other (proxied) device, then the value of name for
                                such an interface is the proxied device's local name for it. If there
                                is no local name, or this object is otherwise not applicable, then
                                this object contains a zero-length string.";
                } // END of name definition.

                container config {
                    description
                        "Configuration data for LLDP-V2 on each interface";
                    uses lldp-v2-interface-config;
                } // END of config-container definition.
                container state {
                    config false;
                    description
                        "Operational state data";
                    uses lldp-v2-interface-config;
                } // END of state-container definition.
                container neighbors {
                    config false;
                    description
                        "LLDP neighbors operational data";
                    uses neighbors-agent-top;
                } // END of neighbors-container definition.
                uses lldp-v2-agent-top;
            } // End of interface-list
        } // END of interfaces-container definition.
    } // END of lldp-interface-top definition.

    grouping  lldp-grouping {
    description
        "LLDP global level information";
    container lldp {
        description
            "LLDP global level information";
        uses lldp-global-top;
        uses lldp-interface-top;
    } // END of lldp-container definition.
    } // END of lldp-grouping definition.

    uses lldp-grouping;

    rpc lldp-debug-on {
        description "This rpc is for configure lldp debugs";
        input  {
            leaf debug-options  {
                type ipi-lldp-types:lldp_debug_t;
                mandatory true;
                description "";
            }
        }
    }

    rpc lldp-debug-off {
        description "This rpc is for delete lldp debugs";
        input  {
            leaf debug-options  {
                type ipi-lldp-types:lldp_debug_t;
                mandatory true;
                description "";
            }
        }
    }

    rpc clear-lldp-counter {
        description "This rpc is for clearing lldp counters on all interfaces";
        input  {
            leaf interface-name  {
                type string;
                description "Name of the interface to clear counters for. Specify NULL to clear
                            counters for all interfaces";
            }
        }
    }

    rpc lldp-snmp-restart {
        description "Use this rpc to restart SNMP for LLDPv2";
    }

    notification lldp-remote-inserts-notification {

        description "Counter for number of times complete set of information advertised by a particular MSAP has been inserted into tables..";

        // eventClass "STATE";
        leaf remote-inserts {
            type  yang:counter32;
        description
            "Counter for number of times complete set of information
                    advertised by a particular MSAP has been inserted into tables";
        }
    }

    notification lldp-remote-deletes-notification {

        description "Counter for numer of times the complete set of information advertised by a particular MSAP has been deleted from tables..";

        // eventClass "STATE";
        leaf remote-deletes {
            type  yang:counter32;
        description
            "Counter for numer of times the complete set of information
                    advertised by a particular MSAP has been deleted from
                    tables.";
        }
    }

}

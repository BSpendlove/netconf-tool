/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ssh.yang
*
*/

module ipi-ssh {

    yang-version 1.1;

    namespace   "http://www.ipinfusion.com/yang/ocnos/ipi-ssh";

    prefix "ipi-ssh";

    import cml-data-types {
        prefix cml-data-types;
        revision-date 2022-04-04;
    }

    import ipi-ssh-types {
        prefix ipi-ssh-types;
        revision-date 2021-09-03;
    }

    import ipi-network-instance {
        prefix ipi-network-instance;
        revision-date 2021-11-10;
    }

    import ipi-vrf {
        prefix ipi-vrf;
        revision-date 2021-09-03;
    }

    import ipi-user-management {
        prefix ipi-user-management;
        revision-date 2022-01-14;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "Data model for SSH Module";


    revision "2021-09-03" {
        description "Update descriptions of attribute";
        reference " 0.3.0.";
    }

    revision "2021-08-02" {
        description "Updated default values for SSH key generation RPCs";
        reference " 0.2.0.";
    }

    revision "2021-07-14" {
        description "Initial Version";
        reference " 0.1.0.";
    }

    grouping ssh-server-config {
        description
            "SSH Server Configurations";
        leaf vrf-name  {
            type  leafref {
                path  "/ipi-network-instance:network-instances/ipi-network-instance:network-instance/ipi-vrf:vrf/ipi-vrf:config/ipi-vrf:vrf-name";
            }
            description "VRF Name associated with this instance";
        } // END of vrf-name definition.

        leaf enable  {
            if-feature feature-list:HAVE_SSH_SERVER;
            type  boolean;
            mandatory true;
            description "Use this attribute to enable the SSH server.";
        } // END of enable definition.

        leaf port  {
            if-feature feature-list:HAVE_SSH_SERVER;
            type  uint32 {
                 range "1024..65535"  {
                    description "1024..65535:ssh server port";
                 }
            }
            description "Use this attribute to set the port number on which the SSH server
                        listens for connections. The default port on which the SSH server
                        listens is 22.";
        } // END of port definition.

        leaf session-limit  {
            if-feature feature-list:HAVE_SSH_SERVER;
            type  uint8 {
                 range "1..40"  {
                    description "1..40:ssh server sessions";
                 }
            }
            description "Use this attribute to set the maximum number of simultaneous sessions
                        allowed. By default, 40 ssh-telnet sessions are allowed";
        } // END of session-limit definition.

        leaf max-login-attempts  {
            if-feature feature-list:HAVE_SSH_SERVER;
            type  uint8 {
                 range "1..3"  {
                    description "1..3:Retries attempts, default is 3 attempts";
                 }
            }
            default "3";
            description "Use this attribute to set the number of times that a user can try to
                        log in to a SSH session.";
        } // END of max-login-attempts definition.

    } // END of ssh-server-config definition.
    grouping ssh-server-encryption-algorithms-config {
        description
            "SSH Server Enryption Algorithm Configurations";
        leaf aes128-ctr  {
            type  empty;
            description "Use this attribute to set the AES128-CTR Cipher";
        } // END of aes128-ctr definition.

        leaf aes192-ctr  {
            type  empty;
            description "Use this attribute to set the AES192-CTR Cipher";
        } // END of aes192-ctr definition.

        leaf aes256-ctr  {
            type  empty;
            description "Use this attribute to set the AES256-CTR Cipher";
        } // END of aes256-ctr definition.

        leaf aes128-cbc  {
            type  empty;
            description "Use this attribute to set the AES128-CBC Cipher";
        } // END of aes128-cbc definition.

        leaf aes192-cbc  {
            type  empty;
            description "Use this attribute to set the AES192-CBC Cipher";
        } // END of aes192-cbc definition.

        leaf aes256-cbc  {
            type  empty;
            description "Use this attribute to set the AES256-CBC Cipher";
        } // END of aes256-cbc definition.

        leaf triple-des-cbc  {
            type  empty;
            description "Use this attribute to set the 3DES-CBC Cipher";
        } // END of triple-des-cbc definition.

    } // END of ssh-server-encryption-algorithms-config definition.
    grouping ssh-server-debug-config {
        description
            "SSH Server debug configurations";
        leaf enable  {
            type  empty;
            description "Use this attribute to enable ssh debugging configurations";
        } // END of enable definition.

    } // END of ssh-server-debug-config definition.
    grouping ssh-server-debug-state {
        description
            "SSH Server debug state information";
        leaf terminal-debug-status  {
            type  cml-data-types:cml_on_off_t;
            description "Use this attribute to display ssh terminal debugging information.";
        } // END of terminal-debug-status definition.

    } // END of ssh-server-debug-state definition.
    grouping ssh-user-keys-config {
        description
            "SSH User Keys configurations";
        leaf-list public-key  {
            type  ipi-ssh-types:ssh_public_key_t {
                length "1..1965";
            }
            description "Use this attribute to set the ssh public-key";
        } // END of public-key definition.

    } // END of ssh-user-keys-config definition.
    grouping ssh-server-top {
        description
            "SSH Server top configurations";
        container vrfs {
            description
                "ssh vrf configurations";

            list vrf {
                key "vrf-name";
                description
                    "ssh vrf instance configurations";
                leaf vrf-name  {
                    type  leafref {
                        path  "../config/vrf-name";
                    }
                    description "VPN routing/forwarding Instance name";
                } // END of vrf-name definition.

                container config {
                    description
                        "config container for ssh vrf instance configurations";
                    uses ssh-server-config;
                } // END of config-container definition.
                container state {
                    config false;
                    description
                        "state container for ssh vrf instance configurations";
                    uses ssh-server-config;
                } // END of state-container definition.
                container encryption-algorithms {
                    if-feature feature-list:HAVE_SSH_SERVER;
                    description
                        "SSH Server Encryption Algorithm Configurations";
                    container config {
                        description
                            "config container for ssh server encryption algorithm configurations";
                        uses ssh-server-encryption-algorithms-config;
                    } // END of config-container definition.
                    container state {
                        config false;
                        description
                            "state container for ssh server encryption algorithm configurations";
                        uses ssh-server-encryption-algorithms-config;
                    } // END of state-container definition.
                } // END of encryption-algorithms-container definition.
            } // End of vrf-list
        } // END of vrfs-container definition.
    } // END of ssh-server-top definition.
    grouping user-ssh-keypair-attributes {
        description
            "user ssh keypair attributes";
        leaf rsa-key  {
            type  ipi-ssh-types:ssh_public_key_t {
                length "1..1965";
            }
            description "User specific Rivest, Shamir, and Adelman (RSA) public-key
                        cryptography SSH server key";
        } // END of rsa-key definition.

        leaf dsa-key  {
            type  ipi-ssh-types:ssh_public_key_t {
                length "1..1965";
            }
            description "User specific Digital System Algorithm (DSA) SSH key";
        } // END of dsa-key definition.

        leaf fingerprint-rsa  {
            type  ipi-ssh-types:ssh_public_key_t {
                length "1..1965";
            }
            description "MD5 over the binary data within the Base64-encoded RSA public key";
        } // END of fingerprint-rsa definition.

        leaf fingerprint-dsa  {
            type  ipi-ssh-types:ssh_public_key_t {
                length "1..1965";
            }
            description "MD5 over the binary data within the Base64-encoded DSA public key";
        } // END of fingerprint-dsa definition.

    } // END of user-ssh-keypair-attributes definition.

    grouping  ssh-server-grouping {
    description
        "ssh-server configurations";
    container ssh-server {
        description
            "ssh-server configurations";
        container debug {
            description
                "ssh debug configurations";
            container config {
                description
                    "config container for ssh debug configurations";
                uses ssh-server-debug-config;
            } // END of config-container definition.
            container state {
                config false;
                description
                    "state container for ssh debug configurations";
                uses ssh-server-debug-config;
                uses ssh-server-debug-state;
            } // END of state-container definition.
        } // END of debug-container definition.
        uses ssh-server-top;
    } // END of ssh-server-container definition.
    } // END of ssh-server-grouping definition.

    grouping  ssh-keys-grouping {
    description
        "ssh-keys configurations";
    container ssh-keys {
        description
            "ssh-keys configurations";
        container config {
            description
                "config container for ssh keys configurations";
            uses ssh-user-keys-config;
        } // END of config-container definition.
        container state {
            config false;
            description
                "state container for ssh keys configurations";
            uses ssh-user-keys-config;
            uses user-ssh-keypair-attributes;
        } // END of state-container definition.
    } // END of ssh-keys-container definition.
    } // END of ssh-keys-grouping definition.

    uses ssh-server-grouping;
    augment /ipi-user-management:user-management/ipi-user-management:users/ipi-user-management:user {
        description
            "ssh-keys configurations";
        uses ssh-keys-grouping;
    }


    rpc ssh-terminal-debugging-on {
        description "Use this RPC to enable debugging for ssh server";
    }

    rpc ssh-terminal-debugging-off {
        description "Use this RPC to disable debugging for ssh server";
    }

    rpc ssh-clear-hosts {
        description "Use this RPC to clear all ssh hosts";
    }

    rpc ssh-generate-server-dsa-key {
        description "Use this attribute to generate ssh host key using DSA Algorithm";
        input  {
            leaf vrf-name  {
                type string;
                default "default";
                description "VPN routing/forwarding Instance name";
            }
            leaf force  {
                type boolean;
                default false;
                description "Use this attribute to overwrite the existing dsa host key";
            }
        }
    }

    rpc ssh-generate-server-rsa-key {
        description "Use this attribute to generate ssh host key using RSA Algorithm";
        input  {
            leaf length  {
                type uint32 {
                    range "1024..4096";
                }
                default "2048";
                description "Use this attribute to set the key-length";
            }
            leaf vrf-name  {
                type string;
                default "default";
                description "VPN routing/forwarding Instance name";
            }
            leaf force  {
                type boolean;
                default false;
                description "Use this attribute to overwrite the existing rsa host key";
            }
        }
    }

    rpc ssh-generate-server-ecdsa-key {
        description "Use this attribute to generate ssh host key using ECDSA Algorithm";
        input  {
            leaf length  {
                type ipi-ssh-types:ssh_ecdsa_key_len_t;
                default "521";
                description "Use this attribute to set the key length";
            }
            leaf vrf-name  {
                type string;
                default "default";
                description "VPN routing/forwarding Instance name";
            }
            leaf force  {
                type boolean;
                default false;
                description "Use this attribute to overwrite the existing ecdsa key";
            }
        }
    }

    rpc ssh-generate-server-ed25519-key {
        description "Use this attribute to generate ssh host key using ED25519 Algorithm";
        input  {
            leaf vrf-name  {
                type string;
                default "default";
                description "VPN routing/forwarding Instance name";
            }
            leaf force  {
                type boolean;
                default false;
                description "Use this attribute to overwrite the existing ed25519 key";
            }
        }
    }

    rpc ssh-clear-server-keys {
        description "Use this attribute to delete ssh host keys";
        input  {
            leaf type  {
                type ipi-ssh-types:ssh_host_key_type_t;
                default "all-keys";
                description "Use this attribute to specify the host-key type";
            }
            leaf vrf-name  {
                type string;
                default "default";
                description "VPN routing/forwarding Instance name";
            }
        }
    }

    rpc ssh-generate-user-rsa-key {
        description "Use this attribute to generate RSA key for a user account";
        input  {
            leaf user-name  {
                type string;
                mandatory true;
                description "Use this attribute to set the username";
            }
            leaf length  {
                type uint32 {
                    range "1024..4096";
                }
                default "4096";
                description "Use this attribute to set the key length";
            }
            leaf force  {
                type boolean;
                default false;
                description "Use this attribute to overwrite the rsa key";
            }
        }
    }

    rpc ssh-generate-user-dsa-key {
        description "Use this attribute to generate DSA key for a user account";
        input  {
            leaf user-name  {
                type string;
                mandatory true;
                description "Use this attribute to set the username";
            }
            leaf force  {
                type boolean;
                default false;
                description "Use this attribute to overwrite the dsa key";
            }
        }
    }

    rpc ssh-clear-user-keys {
        description "Use this attribute to clear a user account's keys";
        input  {
            leaf user-name  {
                type string;
                mandatory true;
                description "Use this attribute to set the username";
            }
        }
    }

}

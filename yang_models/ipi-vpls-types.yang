/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-vpls-types.yang
*
*/

module ipi-vpls-types {

    yang-version 1.1;

    namespace   "http://www.ipinfusion.com/yang/ocnos/ipi-vpls-types";

    prefix "ipi-vpls-types";

    organization
        "IP Infusion Inc.";

    contact
        "Address: 3965 Freedom Circle, Suite 200, Santa Clara, CA 95054
         Phone: +1 408-400-1900
         E-mail: support@ipinfusion.com
         Web: http://www.ipinfusion.com/";

    description
        "Generic VPLS data Types";


    revision "2022-02-16" {
        description "Updated VPLS_PEER_STATE_T enum value";
        reference "Initial Version";
    }

    revision "2021-09-03" {
        description "Update descriptions of attribute";
        reference "Initial Version";
    }

    revision "2021-08-03" {
        description "Added a new value for VPLS_SVC_TPID_T";
        reference "Initial Version";
    }

    revision "2020-08-11" {
        description "Datamodel restructuring";
        reference "Initial Version";
    }



    typedef  vpls_ac_admin_status_t {
        type enumeration {
            enum down {
                value 0;
                description "Set the admin role as Down";
            }
        }
        description "type definition for VPLS_AC_ADMIN_STATUS_T";
    }

    typedef  vpls_peer_state_t {
        type enumeration {
            enum down {
                value 0;
                description "Pseudowire state with peer as Down";
            }
            enum up {
                value 4;
                description "Pseudowire state with peer as UP";
            }
        }
        description "type definition for VPLS_PEER_STATE_T";
    }

    typedef  vpls_signaling_type_t {
        type enumeration {
            enum NA {
                value 0;
                description "No Signaling protocol";
            }
            enum static {
                value 1;
                description "No protocol";
            }
            enum bgp {
                value 2;
                description "Signalig Protocol BGP";
            }
            enum ldp {
                value 4;
                description "Signalig Protocol LDP";
            }
            enum ad-ldp {
                value 8;
                description "Signaling protocol auto-Discovered LDP";
            }
        }
        description "type definition for VPLS_SIGNALING_TYPE_T";
    }

    typedef  vpls_pseudowire_status_t {
        type enumeration {
            enum standby {
                value 0;
                description "Pseudowire status as Standby";
            }
            enum active {
                value 1;
                description "Pseudowire status as Active";
            }
        }
        description "type definition for VPLS_PSEUDOWIRE_STATUS_T";
    }

    typedef  vpls_ac_status_t {
        type enumeration {
            enum up {
                value 0;
                description "the AC is UP";
            }
            enum down {
                value 1;
                description "the AC is Down";
            }
        }
        description "type definition for VPLS_AC_STATUS_T";
    }

    typedef  vpls_mac_learning_t {
        type enumeration {
            enum enable {
                value 1;
                description "Enable MAC learning";
            }
            enum disable {
                value 2;
                description "Disable MAC learning";
            }
        }
        description "type definition for VPLS_MAC_LEARNING_T";
    }

    typedef  vpls_qos_map_profile_type_t {
        type enumeration {
            enum cos-to-queue {
                value 0;
                description "profile for cos to queue map";
            }
            enum queue-color-to-cos {
                value 1;
                description "profile for queue color to cos map";
            }
        }
        description "type definition for VPLS_QOS_MAP_PROFILE_TYPE_T";
    }

    typedef  vpls_svc_tpid_t {
        type enumeration {
            enum dot1.q {
                value 33024;
                description "Set tpid value as 0x8100";
            }
            enum dot1.ad {
                value 34984;
                description "Set tpid value as 0x88a8";
            }
            enum 0x9100 {
                value 37120;
                description "Set tpid value as 0x9100";
            }
            enum 0x9200 {
                value 37376;
                description "Set tpid value as 0x9200";
            }
        }
        description "type definition for VPLS_SVC_TPID_T";
    }

    typedef  vpls_vc_spoke_type_t {
        type enumeration {
            enum vlan {
                value 4;
                description "VC Spoke type:VLAN";
            }
            enum ethernet {
                value 5;
                description "VC Spoke type:Ethernet";
            }
        }
        description "type definition for VPLS_VC_SPOKE_TYPE_T";
    }

    typedef  vpls_port_type_t {
        type enumeration {
            enum access-port {
                value 1;
                description "Access interface statistics counters";
            }
            enum network-port {
                value 2;
                description "Network interface statistics counters";
            }
        }
        description "type definition for VPLS_PORT_TYPE_T";
    }

    typedef  vpls_spoke_vc_type_t {
        type string;
        description "type definition for VPLS_SPOKE_VC_TYPE_T";
    }

    typedef  vpls_peer_type_t {
        type enumeration {
            enum manual {
                value 1;
                description "No signaling is used to set-up the Virtual Circuit";
            }
        }
        description "type definition for VPLS_PEER_TYPE_T";
    }

    typedef  vpls_vc_type_t {
        type enumeration {
            enum vlan {
                value 4;
                description "VLAN";
            }
            enum ethernet {
                value 5;
                description "Ethernet";
            }
        }
        description "type definition for VPLS_VC_TYPE_T";
    }

    typedef  vpls_peer_address_type_t {
        type string;
        description "type definition for VPLS_PEER_ADDRESS_TYPE_T";
    }

    typedef  vpls_vlan_interface_t {
        type string;
        description "type definition for VPLS_VLAN_INTERFACE_T";
    }

    typedef  vpls_mpls_if_ether_t {
        type enumeration {
            enum ethernet {
                value 0;
                description "Ethernet";
            }
        }
        description "type definition for VPLS_MPLS_IF_ETHER_T";
    }

    typedef  vpls_mpls_access_type_t {
        type union {
            type vpls_vlan_interface_t {

            }
            type vpls_mpls_if_ether_t {

            }
        }
        description "type definition for VPLS_MPLS_ACCESS_TYPE_T";
    }

}

/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-cross-connect.yang
*
*/

module ipi-cross-connect {

    yang-version 1.1;

    namespace   "http://www.ipinfusion.com/yang/ocnos/ipi-cross-connect";

    prefix "ipi-cross-connect";

    import cml-data-types {
        prefix cml-data-types;
        revision-date 2022-04-04;
    }

    import ipi-cross-connect-types {
        prefix ipi-cross-connect-types;
        revision-date 2021-11-10;
    }

    import ipi-network-instance {
        prefix ipi-network-instance;
        revision-date 2021-11-10;
    }

    organization
        "IP Infusion Inc.";

    contact
        "Address: 3965 Freedom Circle, Suite 200, Santa Clara, CA 95054
         Phone: +1 408-400-1900
         E-mail: support@ipinfusion.com
         Web: http://www.ipinfusion.com/";

    description
        "Cross-Connect configurations";


    revision "2022-01-17" {
        description "Add attribute xc-name to cross-connect config container.";
        reference " 0.1.1.";
    }

    revision "2021-11-10" {
        description "It was moved from interfaces extended datamodel to network-instances datamodel.";
        reference " 0.1.0.";
    }

    grouping cross-connect-config {
        description
            "Grouping for Cross-Connect configurations";
        leaf xc-name  {
            type  leafref {
                path  "/ipi-network-instance:network-instances/ipi-network-instance:network-instance/ipi-network-instance:instance-name";
            }
            description "This attribute specifies the entry name for cross-connect";
        } // END of xc-name definition.

        leaf-list endpoint-if  {
            type  string {
                length "1..33";
                pattern "[^?' =,>|]+";
            }
            description "This attribute specifies the endpoint for cross-connect";
        } // END of endpoint-if definition.

        leaf description  {
            type  cml-data-types:cml_line_t {
                length "1..1965";
            }
            description "This attribute specifies the description for cross-connect";
        } // END of description definition.

        leaf admin-disable  {
            type  empty;
            description "This attribute is used to temporarily shutdown the cross-connect";
        } // END of admin-disable definition.

    } // END of cross-connect-config definition.
    grouping cross-connect-state {
        description
            "Grouping for Cross-Connect operational data";
        leaf operational-state  {
            type  ipi-cross-connect-types:xc_oper_status_t;
            description "This attribute shows the current status of cross-connect.";
        } // END of operational-state definition.

    } // END of cross-connect-state definition.

    grouping  cross-connect-grouping {
    description
        "Global container for cross connect between subinterfaces";
    container cross-connect {
        description
            "Global container for cross connect between subinterfaces";
        container config {
            description
                "Global configuration for Cross-Connect";
            uses cross-connect-config;
        } // END of config-container definition.
        container state {
            config false;
            description
                "State data for cross-connect";
            uses cross-connect-config;
            uses cross-connect-state;
        } // END of state-container definition.
    } // END of cross-connect-container definition.
    } // END of cross-connect-grouping definition.

    augment /ipi-network-instance:network-instances/ipi-network-instance:network-instance {
    when " /ipi-network-instance:network-instances/ipi-network-instance:network-instance/ipi-network-instance:instance-type = 'cross-connect' ";
        description
            "Global container for cross connect between subinterfaces";
        uses cross-connect-grouping;
    }


}

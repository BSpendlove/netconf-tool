/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-mcec.yang
*
*/

module ipi-mcec {

    yang-version 1.1;

    namespace   "http://www.ipinfusion.com/yang/ocnos/ipi-mcec";

    prefix "ipi-mcec";

    import ipi-interface {
        prefix ipi-interface;
        revision-date 2022-04-05;
    }

    import ipi-mcec-types {
        prefix ipi-mcec-types;
        revision-date 2021-04-19;
    }

    import ietf-inet-types {
        prefix inet;
        revision-date 2013-07-15;
    }

    import ipi-network-instance {
        prefix ipi-network-instance;
        revision-date 2021-11-10;
    }

    import ipi-vrf {
        prefix ipi-vrf;
        revision-date 2021-09-03;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "Multi Chassis Ethernet Channel (MCEC)";


    revision "2021-11-15" {
        description "IDP CLI applicable only for DUNE platform";
        reference " 0.4.0.";
    }

    revision "2021-10-14" {
        description "Separate IDL and IDP in different containers";
        reference " 0.3.2.";
    }

    revision "2021-10-02" {
        description "Remove the when clause in the vrf attribute pointed to the intra-domain-link";
        reference " 0.3.1.";
    }

    revision "2021-08-03" {
        description "Added implicit delete in mcec-switchover-type config container";
        reference " 0.3.0.";
    }

    revision "2021-06-01" {
        description "Remove the when statement pointed to the vrf path in the intra-domain-peer";
        reference " 0.2.7.";
    }

    revision "2021-05-25" {
        description "Remove attribute entry-id from local and remote mac tables";
        reference " 0.2.6.";
    }

    revision "2021-05-24" {
        description "Updated the relationship between attributes for intra-domain-peer config";
        reference " 0.2.5.";
    }

    revision "2021-05-23" {
        description "Dropped the attribute stp-state from yang";
        reference " 0.2.4.";
    }

    revision "2021-04-26" {
        description "Dropped the attribute aggregation-key from yang";
        reference " 0.2.3.";
    }

    revision "2021-04-06" {
        description "Changed the intra-domain-link to be a leafref to ipi-interface";
        reference " 0.2.2.";
    }

    revision "2021-03-24" {
        description "Change on how switchover behaves according to interface mode";
        reference " 0.2.1.";
    }

    revision "2021-03-06" {
        description "Restructured module as per open-config";
        reference " 0.2.0.";
    }

    revision "2018-06-21" {
        description "Initial Version";
        reference " 0.1.0.";
    }

    grouping mcec-debug-config {
        description
            "Grouping for mcec debug configuration";
        leaf options  {
            type  ipi-mcec-types:mcec_debug_t;
            description "Use this attribute to debug the mlag feature.";
        } // END of options definition.

    } // END of mcec-debug-config definition.
    grouping mcec-debug-terminal-state {
        description
            "Grouping for terminal debug operational state";
        leaf options  {
            type  ipi-mcec-types:mcec_debug_t;
            description "Use this attribute to debug the mlag feature in terminal.";
        } // END of options definition.

    } // END of mcec-debug-terminal-state definition.
    grouping mcec-debug-top {
        description
            "Grouping for mcec debug configuration";
        container debug {
            description
                "Debugging functions";
            container config {
                description
                    "Configuration data";
                uses mcec-debug-config;
            } // END of config-container definition.
            container state {
                config false;
                description
                    "Operational state data";
                container terminal {
                    config false;
                    description
                        "Terminal debug operational state";
                    uses mcec-debug-terminal-state;
                } // END of terminal-container definition.
                uses mcec-debug-config;
            } // END of state-container definition.
        } // END of debug-container definition.
    } // END of mcec-debug-top definition.
    grouping mcec-domain-config {
        description
            "Grouping for mcec domain configuration";
        leaf system-number  {
            type  uint8 {
                 range "1..2"  {
                    description "1..2:Domain System Number";
                 }
            }
            description "Use this attribute to configure domain system number, which uniquely
                        identifies domain system in MCEC domain";
        } // END of system-number definition.

        leaf address  {
            type  ipi-mcec-types:mcec_domain_addr_t {
                length "1..1965";
            }
            description "Use this attribute configure domain address, which helps to identify
                        the MCEC domain";
        } // END of address definition.

        leaf priority  {
            type  uint16 {
                 range "1..65535"  {
                    description "1..65535:Priority value";
                 }
            }
            default "32768";
            description "Use this attribute to specify the priority value associated with MCEC
                        domain";
        } // END of priority definition.

        leaf hello-timeout  {
            type  ipi-mcec-types:mcec_hello_t;
            default "long";
            description "Use this attribute to specify the domain hello-timeout value";
        } // END of hello-timeout definition.

    } // END of mcec-domain-config definition.
    grouping mcec-domain-info-state {
        description
            "Grouping for mcec domain info state";
        leaf domain-sync  {
            type  ipi-mcec-types:mcec_domain_sync_status_t;
            description "MCEC domain is synchronized between the two nodes";
        } // END of domain-sync definition.

        leaf domain-adjacency  {
            type  ipi-mcec-types:mcec_domain_adjacency_state_t;
            description "Configured MCEC Domain adjacency state formed between the two nodes";
        } // END of domain-adjacency definition.

        leaf mcec-invalid-pdu-rx  {
            type  uint32;
            description "Invalid PDU received for the MCEC domain";
        } // END of mcec-invalid-pdu-rx definition.

    } // END of mcec-domain-info-state definition.
    grouping mcec-domain-top {
        description
            "Grouping for mcec domain configuration";
        container domain {
            description
                "MCEC domain configuration";
            container config {
                description
                    "Configuration data";
                uses mcec-domain-config;
            } // END of config-container definition.
            container state {
                config false;
                description
                    "Operational state data";
                uses mcec-domain-config;
                uses mcec-domain-info-state;
            } // END of state-container definition.
        } // END of domain-container definition.
    } // END of mcec-domain-top definition.
    grouping mcec-instance-state {
        description
            "Grouping for mcec instance states";
        leaf mlag-id  {
            type  uint16;
            description "MLAG-id configured by the user";
        } // END of mlag-id definition.

        leaf interface  {
            type  string {
                length "1..1965";
                pattern "[^?' =,>|]+";
            }
            description "MLAG interface details";
        } // END of interface definition.

        leaf administrative-aggregation-key  {
            type  uint16;
            description "Admin key mapped to the MLAG instance";
        } // END of administrative-aggregation-key definition.

        leaf operational-aggregation-key  {
            type  uint16;
            description "MLAG operational key obtained from the comparison of admin key of both
                        nodes";
        } // END of operational-aggregation-key definition.

        leaf physical-properties-digest  {
            type  string {
                length "1..1965";
                pattern "[^?' =,>|]+";
            }
            description "MD5 digest of the MCEC attributed critical for sync formation";
        } // END of physical-properties-digest definition.

        leaf operational-partner-aggregation-key  {
            type  uint16;
            description "MLAG operational key of the peer node";
        } // END of operational-partner-aggregation-key definition.

        leaf partner-system  {
            type  string {
                length "1..1965";
                pattern "[^?' =,>|]+";
            }
            description "System number of the peer MLAG instance";
        } // END of partner-system definition.

        leaf partner-system-priority  {
            type  uint16;
            description "System priority of the peer MLAG instance";
        } // END of partner-system-priority definition.

        leaf member-interface-bandwidth  {
            type  string {
                length "1..1965";
                pattern "[^?' =,>|]+";
            }
            description "MLAG interface bandwidth";
        } // END of member-interface-bandwidth definition.

        leaf member-interface-state  {
            type  ipi-mcec-types:mcec_if_state_t;
            description "MLAG interface state";
        } // END of member-interface-state definition.

        leaf mlag-sync  {
            type  ipi-mcec-types:mcec_sync_state_t;
            description "MLAG instance sync state between MLAG nodes";
        } // END of mlag-sync definition.

        leaf flood-enabled  {
            type  ipi-mcec-types:mcec_flood_state_t;
            description "Intra-domain-link to MLAG flooding status";
        } // END of flood-enabled definition.

        leaf mlag-port-state  {
            type  ipi-mcec-types:mcec_if_state_t;
            description "MLAG interface state based on user configuration (admin shutdown/admin
                        no-shutdown)";
        } // END of mlag-port-state definition.

        leaf mlag-interface-state  {
            type  ipi-mcec-types:mcec_if_state_t;
            description "MLAG interface state";
        } // END of mlag-interface-state definition.

        leaf aggregation-mapped  {
            type  boolean;
            description "MLAG is mapped to a static aggregator";
        } // END of aggregation-mapped definition.

        leaf mlag-bandwidth  {
            type  string {
                length "1..1965";
                pattern "[^?' =,>|]+";
            }
            description "MLAG interface bandwidth";
        } // END of mlag-bandwidth definition.

        leaf info-receive-state  {
            type  ipi-mcec-types:mcec_info_receive_state_t;
            description "Receive state machine states of MLAG instance";
        } // END of info-receive-state definition.

        leaf info-periodic-tx-state  {
            type  ipi-mcec-types:mcec_info_periodic_tx_state_t;
            description "Transmission state machine states of MLAG instance";
        } // END of info-periodic-tx-state definition.

        leaf valid-info-pdu-rx  {
            type  uint32;
            description "Valid MLAG information PDU received";
        } // END of valid-info-pdu-rx definition.

        leaf valid-info-pdu-tx  {
            type  uint32;
            description "Valid MLAG information PDU transmitted";
        } // END of valid-info-pdu-tx definition.

    } // END of mcec-instance-state definition.
    grouping mcec-instance-neighbor-state {
        description
            "Grouping for mcec instance neighbor states";
        leaf administrative-aggregation-key  {
            type  uint16;
            description "MLAG administrative key received from the peer DSN node";
        } // END of administrative-aggregation-key definition.

        leaf physical-properties-digest  {
            type  string {
                length "1..1965";
                pattern "[^?' =,>|]+";
            }
            description "MD5 physical digest properties of the peer DSN node";
        } // END of physical-properties-digest definition.

        leaf operational-partner-aggregation-key  {
            type  uint16;
            description "MLAG partner aggregation key from the peer DSN node";
        } // END of operational-partner-aggregation-key definition.

        leaf partner-system  {
            type  string {
                length "1..1965";
                pattern "[^?' =,>|]+";
            }
            description "MLAG partner system number received from peer DSN node";
        } // END of partner-system definition.

        leaf partner-system-priority  {
            type  uint16;
            description "MLAG partner system priority received from peer DSN node";
        } // END of partner-system-priority definition.

        leaf member-interface-bandwidth  {
            type  string {
                length "1..1965";
                pattern "[^?' =,>|]+";
            }
            description "MLAG member interface bandwidth from the peer DSN node";
        } // END of member-interface-bandwidth definition.

        leaf member-interface-state  {
            type  ipi-mcec-types:mcec_if_state_t;
            description "MLAG interface state of peer node";
        } // END of member-interface-state definition.

        leaf mlag-sync  {
            type  ipi-mcec-types:mcec_sync_state_t;
            description "Neighbor MLAG interface sync state";
        } // END of mlag-sync definition.

    } // END of mcec-instance-neighbor-state definition.
    grouping mcec-instance-neighbor-top {
        description
            "Grouping for MCEC instance neighbor states";
        container neighbor {
            config false;
            description
                "Container for instance neighbor parameters";
            container state {
                config false;
                description
                    "Operational state data";
                uses mcec-instance-neighbor-state;
            } // END of state-container definition.
        } // END of neighbor-container definition.
    } // END of mcec-instance-neighbor-top definition.
    grouping mcec-instance-top {
        description
            "Grouping for MCEC instance related details";

        list mcec-instance {
            key "mlag-id";
            config false;
            description
                "List of MCEC instance related details";
            leaf mlag-id  {
                type  leafref {
                    path  "../state/mlag-id";
                }
                description "MLAG-id configured by the user";
            } // END of mlag-id definition.

            container state {
                config false;
                description
                    "Operational state data";
                uses mcec-instance-state;
            } // END of state-container definition.
            uses mcec-instance-neighbor-top;
        } // End of mcec-instance-list
    } // END of mcec-instance-top definition.
    grouping mcec-intra-domain-link-config {
        description
            "Grouping for mcec intra domain link configuration";
        leaf interface  {
            type  leafref {
                path  "/ipi-interface:interfaces/ipi-interface:interface/ipi-interface:name";
            }
            description "Use this attribute to map an interface as intra domain link that
                        connects the domain system with its neighbour in a mcec domain";
        } // END of interface definition.

    } // END of mcec-intra-domain-link-config definition.
    grouping mcec-intra-domain-peer-address-config {
        description
            "Grouping for mcec intra domain address configuration";
        leaf peer-address  {
            type  inet:ipv4-address;
            mandatory true;
            description "User configured IPV4 address of the peer DSN node";
        } // END of peer-address definition.

        leaf local-address  {
            type  inet:ipv4-address;
            mandatory true;
            description "User configured IPV4 address of the local node";
        } // END of local-address definition.

        leaf vrf  {
            when " /ipi-mcec:mcec/ipi-mcec:intra-domain/ipi-mcec:peer-address/ipi-mcec:config/ipi-mcec:peer-address ";
            type  leafref {
                path  "/ipi-network-instance:network-instances/ipi-network-instance:network-instance/ipi-vrf:vrf/ipi-vrf:config/ipi-vrf:vrf-name";
            }
            mandatory true;
            description "vrf of the peer DSN node";
        } // END of vrf definition.

    } // END of mcec-intra-domain-peer-address-config definition.
    grouping mcec-idp-neighbor-info-state {
        description
            "Grouping for mcec intra-domain-peer neighbor info state";
        leaf domain-address  {
            type  ipi-mcec-types:mcec_domain_addr_t {
                length "1..1965";
            }
            description "Domain address of the peer node in HHHH.HHHH.HHHH format Values
                        0000.0000.0000 and FFFF.FFFF.FFFF are not valid";
        } // END of domain-address definition.

        leaf domain-priority  {
            type  uint32;
            description "Domain priority of the peer node";
        } // END of domain-priority definition.

        leaf domain-system-number  {
            type  uint16;
            description "Domain system number of the peer node";
        } // END of domain-system-number definition.

        leaf domain-sync  {
            type  ipi-mcec-types:mcec_domain_sync_status_t;
            description "Domain sync flag received from the peer node";
        } // END of domain-sync definition.

        leaf hello-timeout  {
            type  uint16;
            description "MCEC domain timeout of the peer node";
        } // END of hello-timeout definition.

    } // END of mcec-idp-neighbor-info-state definition.
    grouping mcec-idp-neighbor-info-top {
        description
            "Grouping for mcec intra-domain-peer neighbor info state";
        container neighbor-info {
            config false;
            description
                "Neighbor domain details of the peer DSN node";
            container state {
                config false;
                description
                    "Operational state data";
                uses mcec-idp-neighbor-info-state;
            } // END of state-container definition.
        } // END of neighbor-info-container definition.
    } // END of mcec-idp-neighbor-info-top definition.
    grouping mcec-intra-domain-peer-info-state {
        description
            "Grouping for mcec intra-domain-peer info state";
        leaf mcec-hello-periodic-tx-state  {
            type  ipi-mcec-types:mcec_hello_periodic_tx_state_t;
            description "Holds the current state of domain PDU transmission state machine";
        } // END of mcec-hello-periodic-tx-state definition.

        leaf mcec-valid-hello-pdu-rx  {
            type  uint32;
            description "Valid domain PDU received from peer node";
        } // END of mcec-valid-hello-pdu-rx definition.

        leaf mcec-valid-hello-pdu-tx  {
            type  uint32;
            description "Valid domain PDU transmitted to the peer node";
        } // END of mcec-valid-hello-pdu-tx definition.

        leaf mcec-valid-info-pdu-rx  {
            type  uint32;
            description "Valid MLAG information PDU received from peer node";
        } // END of mcec-valid-info-pdu-rx definition.

        leaf mcec-valid-info-pdu-tx  {
            type  uint32;
            description "Valid MLAG information PDU transmitted to peer node";
        } // END of mcec-valid-info-pdu-tx definition.

        leaf mcec-valid-mac-sync-pdu-rx  {
            type  uint32;
            description "Valid MLAG MAC synchronized PDU received from peer node";
        } // END of mcec-valid-mac-sync-pdu-rx definition.

        leaf mcec-valid-mac-sync-pdu-tx  {
            type  uint32;
            description "Valid MLAG MAC synchronized PDU transmitted to peer node";
        } // END of mcec-valid-mac-sync-pdu-tx definition.

    } // END of mcec-intra-domain-peer-info-state definition.
    grouping mcec-intra-domain-peer-info-top {
        description
            "Grouping for mcec intra-domain-peer info state";
        container intra-domain-peer-info {
            config false;
            description
                "MCEC domain state machine states and counters related";
            container state {
                config false;
                description
                    "Operational state data";
                uses mcec-intra-domain-peer-info-state;
            } // END of state-container definition.
        } // END of intra-domain-peer-info-container definition.
    } // END of mcec-intra-domain-peer-info-top definition.
    grouping mcec-intra-domain-peer-top {
        description
            "Intra-domain-peer is the link between DSN1 and DSN2. Through this
                        link, MLAG domain and information PDUs are exchanged";
        container intra-domain {
            description
                "Intra Domain Peer configuration";
            container peer-link {
                description
                    "Intra Domain Peer link configuration";
                container config {
                    description
                        "Configuration data";
                    uses mcec-intra-domain-link-config;
                } // END of config-container definition.
                container state {
                    config false;
                    description
                        "Operational state data";
                    uses mcec-intra-domain-link-config;
                } // END of state-container definition.
            } // END of peer-link-container definition.
            container peer-address {
                if-feature feature-list:HAVE_DUNE;
                description
                    "Intra Domain Peer address configuration";
                container config {
                    presence "yes";
                    description
                        "Configuration data";
                    uses mcec-intra-domain-peer-address-config;
                } // END of config-container definition.
                container state {
                    config false;
                    description
                        "Operational state data";
                    uses mcec-intra-domain-peer-address-config;
                } // END of state-container definition.
            } // END of peer-address-container definition.
            uses mcec-idp-neighbor-info-top;
            uses mcec-intra-domain-peer-info-top;
        } // END of intra-domain-container definition.
    } // END of mcec-intra-domain-peer-top definition.
    grouping mcec-mac-sync-state {
        description
            "Grouping for mac sync states";
    } // END of mcec-mac-sync-state definition.
    grouping mcec-mac-table-state {
        description
            "Grouping for mac table states";
        leaf mac-address  {
            type  string {
                length "1..1965";
                pattern "[^?' =,>|]+";
            }
            description "MAC address that are learnt on the local node";
        } // END of mac-address definition.

        leaf vlan-id  {
            type  uint16;
            description "Vlan-id of the MAC address it belongs to";
        } // END of vlan-id definition.

        leaf output-interface  {
            type  string {
                length "1..1965";
                pattern "[^?' =,>|]+";
            }
            description "Interface on which the remote MAC entry is learnt";
        } // END of output-interface definition.

    } // END of mcec-mac-table-state definition.
    grouping mcec-local-mac-table-top {
        description
            "Grouping for local mac table states";

        list local-mac-table {
            key "mac-address vlan-id";
            config false;
            description
                "List of MAC addresses learnt from the local node";
            leaf mac-address  {
                type  leafref {
                    path  "../state/mac-address";
                }
                description "MAC address that are learnt on the local node";
            } // END of mac-address definition.

            leaf vlan-id  {
                type  leafref {
                    path  "../state/vlan-id";
                }
                description "Vlan-id of the MAC address it belongs to";
            } // END of vlan-id definition.

            container state {
                config false;
                description
                    "Operational state data";
                uses mcec-mac-table-state;
            } // END of state-container definition.
        } // End of local-mac-table-list
    } // END of mcec-local-mac-table-top definition.
    grouping mcec-remote-mac-table-top {
        description
            "Grouping for remote mac table states";

        list remote-mac-table {
            key "mac-address vlan-id";
            config false;
            description
                "MAC address list learnt from the peer node";
            leaf mac-address  {
                type  leafref {
                    path  "../state/mac-address";
                }
                description "MAC address that are learnt on the remote node";
            } // END of mac-address definition.

            leaf vlan-id  {
                type  leafref {
                    path  "../state/vlan-id";
                }
                description "Vlan-id of the MAC address it belongs to";
            } // END of vlan-id definition.

            container state {
                config false;
                description
                    "Operational state data";
                uses mcec-mac-table-state;
            } // END of state-container definition.
        } // End of remote-mac-table-list
    } // END of mcec-remote-mac-table-top definition.
    grouping mcec-mac-sync-top {
        description
            "Grouping for mac sync states";
        container mac-sync {
            config false;
            description
                "Container for dynamic MAC address synchronized between the MLAG nodes";
            uses mcec-local-mac-table-top;
            uses mcec-remote-mac-table-top;
        } // END of mac-sync-container definition.
    } // END of mcec-mac-sync-top definition.
    grouping mcec-stp-sync-state {
        description
            "Grouping for stp sync states";
        leaf bridge-priority  {
            type  uint16;
            description "Bridge priority of the node that will be used for STP";
        } // END of bridge-priority definition.

        leaf path-cost-method  {
            type  uint8;
            description "The metric STP uses to calculate the shortest path";
        } // END of path-cost-method definition.

        leaf domain-digest  {
            type  string {
                length "1..1965";
                pattern "[^?' =,>|]+";
            }
            description "STP domain digest used for MCEC";
        } // END of domain-digest definition.

        leaf neighbor-domain-digest  {
            type  string {
                length "1..1965";
                pattern "[^?' =,>|]+";
            }
            description "Peer STP domain digest received for the MCEC";
        } // END of neighbor-domain-digest definition.

    } // END of mcec-stp-sync-state definition.
    grouping mcec-stp-sync-mlag-interface-entry-state {
        description
            "Grouping for stp mlag interface entry states";
        leaf mlag-id  {
            type  uint16;
            description "User configured MLAG-id";
        } // END of mlag-id definition.

        leaf port-priority  {
            type  uint16;
            description "MLAG interface priority that will be used in STP";
        } // END of port-priority definition.

        leaf path-cost  {
            type  uint32;
            description "MLAG interface path cost that will be used on STP";
        } // END of path-cost definition.

        leaf interface-digest  {
            type  string {
                length "1..1965";
                pattern "[^?' =,>|]+";
            }
            description "Used to form STP sync between the two MLAG nodes";
        } // END of interface-digest definition.

        leaf neighbor-interface-digest  {
            type  string {
                length "1..1965";
                pattern "[^?' =,>|]+";
            }
            description "Neighbor MLAG interface digest received from the peer node";
        } // END of neighbor-interface-digest definition.

    } // END of mcec-stp-sync-mlag-interface-entry-state definition.
    grouping mcec-stp-mlag-interface-sync-top {
        description
            "Grouping for stp mlag interface sync states";

        list mlag-interface-sync-entry {
            key "mlag-id";
            config false;
            description
                "List of mlag interface sync entries participating in STP";
            leaf mlag-id  {
                type  leafref {
                    path  "../state/mlag-id";
                }
                description "User configured MLAG-id";
            } // END of mlag-id definition.

            container state {
                config false;
                description
                    "Operational state data";
                uses mcec-stp-sync-mlag-interface-entry-state;
            } // END of state-container definition.
        } // End of mlag-interface-sync-entry-list
    } // END of mcec-stp-mlag-interface-sync-top definition.
    grouping mcec-stp-sync-top {
        description
            "Grouping for stp sync states";
        container stp-sync {
            config false;
            description
                "STP synchronization details related with MCEC";
            container state {
                config false;
                description
                    "Operational state data";
                uses mcec-stp-sync-state;
            } // END of state-container definition.
            uses mcec-stp-mlag-interface-sync-top;
        } // END of stp-sync-container definition.
    } // END of mcec-stp-sync-top definition.
    grouping mcec-mlag-interface-config {
        description
            "Grouping for mlag interface configuration";
        leaf interface-mode  {
            type  ipi-mcec-types:mcec_mode_type_t;
            default "active-standby";
            description "Use this attribute to set the MC-LAG mode. active-standby: The
                        interface is ready to transition from active to standby state should a
                        failure occur in the other node.";
        } // END of interface-mode definition.

    } // END of mcec-mlag-interface-config definition.
    grouping mcec-switchover-type-config {
        description
            "Grouping for switchover type configuration";
        leaf revertive-timer  {
            when " /ipi-mcec:mcec/ipi-mcec:mlag-interface/ipi-mcec:switchover-type/ipi-mcec:config/ipi-mcec:enable-non-revertive != '1' + /ipi-mcec:mcec/ipi-mcec:mlag-interface/ipi-mcec:config/ipi-mcec:interface-mode != '1' ";
            type  uint8 {
                 range "1..255"  {
                    description "1..255:Revertive switchover timer value in seconds";
                 }
            }
            default "10";
            description "Use this attribute to set the timer for MC-LAG switchover revertive
                        type. After Revertive timer expires Slave will handover the control to
                        Master Node.
                        If a failure happens that triggers a switchover, after failure
                        recovery the initially-active node becomes active again. Default
                        switchover type is revertive 10s.";
        } // END of revertive-timer definition.

        leaf enable-non-revertive  {
            when " /ipi-mcec:mcec/ipi-mcec:mlag-interface/ipi-mcec:config/ipi-mcec:interface-mode != '1' + not(/ipi-mcec:mcec/ipi-mcec:mlag-interface/ipi-mcec:switchover-type/ipi-mcec:config/ipi-mcec:revertive-timer) ";
            type  empty;
            description "Use this attribute to set the MC-LAG switchover to non-revertive type.
                        Do not switch back to the initially-active node after failure
                        recovery. Default switchover type is revertive 10s.";
        } // END of enable-non-revertive definition.

    } // END of mcec-switchover-type-config definition.
    grouping mcec-switchover-type-top {
        description
            "Grouping for switchover type configuration";
        container switchover-type {
            description
                "Container for switchover type parameters";
            container config {
                description
                    "Configuration data";
                uses mcec-switchover-type-config;
            } // END of config-container definition.
            container state {
                config false;
                description
                    "Operational state data";
                uses mcec-switchover-type-config;
            } // END of state-container definition.
        } // END of switchover-type-container definition.
    } // END of mcec-switchover-type-top definition.
    grouping mcec-mlag-interface-top {
        description
            "Grouping for MLAG interface details";

        list mlag-interface {
            key "name";
            description
                "List of MLAG interfaces";
            leaf name  {
                type  leafref {
                    path  "/ipi-interface:interfaces/ipi-interface:interface/ipi-interface:name";
                }
                description "User specified MLAG interface name";
            } // END of name definition.

            container config {
                description
                    "Configuration data";
                uses mcec-mlag-interface-config;
            } // END of config-container definition.
            container state {
                config false;
                description
                    "Operational state data";
                uses mcec-mlag-interface-config;
            } // END of state-container definition.
            uses mcec-switchover-type-top;
        } // End of mlag-interface-list
    } // END of mcec-mlag-interface-top definition.

    grouping  mcec-grouping {
    description
        "Multi-Chassis-Ethernet-Channel";
    container mcec {
        description
            "Multi-Chassis-Ethernet-Channel";
        uses mcec-debug-top;
        uses mcec-domain-top;
        uses mcec-instance-top;
        uses mcec-intra-domain-peer-top;
        uses mcec-mac-sync-top;
        uses mcec-stp-sync-top;
        uses mcec-mlag-interface-top;
    } // END of mcec-container definition.
    } // END of mcec-grouping definition.

    uses mcec-grouping;

    rpc mcec-terminal-debug-on {
        description "Enable MCEC debug options";
        input  {
            leaf options  {
                type ipi-mcec-types:mcec_debug_t;
                mandatory true;
                description "Bitmap representing MCEC debug options";
            }
        }
    }

    rpc mcec-terminal-debug-off {
        description "Disable MCEC debug options";
        input  {
            leaf options  {
                type ipi-mcec-types:mcec_debug_t;
                mandatory true;
                description "Bitmap representing MCEC debug options";
            }
        }
    }

    rpc clear-mcec-statistics {
        description "Clear mcec statistic";
    }

}

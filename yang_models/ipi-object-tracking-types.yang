/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-object-tracking-types.yang
*
*/

module ipi-object-tracking-types {

    yang-version 1.1;

    namespace   "http://www.ipinfusion.com/yang/ocnos/ipi-object-tracking-types";

    prefix "ipi-object-tracking-types";

    organization
        "IP Infusion Inc.";

    contact
        "Address: 3965 Freedom Circle, Suite 200, Santa Clara, CA 95054
         Phone: +1 408-400-1900
         E-mail: support@ipinfusion.com
         Web: http://www.ipinfusion.com/";

    description
        "Object tracking  module Datatypes";


    revision "2021-12-08" {
        description "Initial version";
        reference " 0.1.0.";
    }



    typedef  object_tracking_reachability_status_t {
        type enumeration {
            enum down {
                value 0;
                description "None";
            }
            enum up {
                value 1;
                description "None";
            }
        }
        description "type definition for OBJECT_TRACKING_REACHABILITY_STATUS_T";
    }

}

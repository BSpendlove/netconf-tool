/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-routemap-types.yang
*
*/

module ipi-routemap-types {

    yang-version 1.1;

    namespace   "http://www.ipinfusion.com/yang/ocnos/ipi-routemap-types";

    prefix "ipi-routemap-types";

    import ietf-inet-types {
        prefix inet;
        revision-date 2013-07-15;
    }

    organization
        "IP Infusion Inc.";

    contact
        "Address: 3965 Freedom Circle, Suite 200, Santa Clara, CA 95054
         Phone: +1 408-400-1900
         E-mail: support@ipinfusion.com
         Web: http://www.ipinfusion.com/";

    description
        "YANG version of the ipi-routemap-types";


    revision "2021-09-03" {
        description "Update descriptions of attribute";
        reference " 0.3.0.";
    }

    revision "2020-12-15" {
        description "Change to have data-types in lower case instead of camel case";
        reference " 0.2.0.";
    }

    revision "2020-08-30" {
        description "Initial Version";
        reference " 0.1.0.";
    }



    typedef  rmap_action_type_t {
        type enumeration {
            enum permit {
                value 0;
                description "Route map permits set operations";
            }
            enum deny {
                value 1;
                description "Route map denies set operations";
            }
        }
        description "type definition for RMAP_ACTION_TYPE_T";
    }

    typedef  rmap_route_type_t {
        type enumeration {
            enum type-1 {
                value 1;
                description "Match OSPF External Type 1 metrics";
            }
            enum type-2 {
                value 2;
                description "Match OSPF External Type 2 metrics";
            }
        }
        description "type definition for RMAP_ROUTE_TYPE_T";
    }

    typedef  rmap_origin_type_t {
        type enumeration {
            enum egp {
                value 1;
                description "remote EGP";
            }
            enum igp {
                value 2;
                description "local IGP";
            }
            enum incomplete {
                value 3;
                description "unknown heritage";
            }
        }
        description "type definition for RMAP_ORIGIN_TYPE_T";
    }

    typedef  rmap_community_string_t {
        type union {
            type int32 {
                range "1..99 | 100..500";

            }
            type string {

            }
        }
        description "type definition for RMAP_COMMUNITY_STRING_T";
    }

    typedef  rmap_ipv6_nexthop_t {
        type union {
            type string {

            }
            type inet:ipv6-address {

            }
        }
        description "type definition for RMAP_IPV6_NEXTHOP_T";
    }

    typedef  rmap_community_type_t {
        type enumeration {
            enum no-exact-match {
                value 0;
                description "Not do exact matching of communities";
            }
            enum exact-match {
                value 1;
                description "Do exact matching of communities";
            }
        }
        description "type definition for RMAP_COMMUNITY_TYPE_T";
    }

    typedef  rmap_forward_interface_type_t {
        type enumeration {
            enum null0 {
                value 0;
                description "Forward to no interface";
            }
            enum tunnel-te {
                value 1;
                description "Forward to MPLS-TE tunnel";
            }
        }
        description "type definition for RMAP_FORWARD_INTERFACE_TYPE_T";
    }

    typedef  rmap_metric_type_t {
        type enumeration {
            enum type-1 {
                value 1;
                description "OSPF external type 1 metric";
            }
            enum type-2 {
                value 2;
                description "OSPF external type 2 metric";
            }
            enum internal {
                value 3;
                description "IS-IS internal metric type";
            }
            enum external {
                value 4;
                description "IS-IS external metric type";
            }
        }
        description "type definition for RMAP_METRIC_TYPE_T";
    }

    typedef  rmap_level_type_t {
        type enumeration {
            enum level-1 {
                value 1;
                description "export into a level-1 area";
            }
            enum level-2 {
                value 2;
                description "export into level-2 sub-domain";
            }
            enum level-1-2 {
                value 3;
                description "export into level-1 and level-2";
            }
        }
        description "type definition for RMAP_LEVEL_TYPE_T";
    }

    typedef  rmap_ext_cost_type_t {
        type enumeration {
            enum no-comparision {
                value 0;
                description "No comparision for cost";
            }
            enum igp {
                value 1;
                description "Compare following IGP cost comparison";
            }
            enum pre-bestpath {
                value 2;
                description "Compare before all other steps in bestpath calculation";
            }
        }
        description "type definition for RMAP_EXT_COST_TYPE_T";
    }

    typedef  rmap_additive_type_t {
        type enumeration {
            enum no-additive {
                value 0;
                description "Don't add to the existing community";
            }
            enum additive {
                value 1;
                description "Add to the existing community";
            }
        }
        description "type definition for RMAP_ADDITIVE_TYPE_T";
    }

}

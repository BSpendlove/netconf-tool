module ipi-oc-rpol-deviations {
  namespace   "http://www.ipinfusion.com/yang/ocnos/ipi-oc-rpol-deviations";
  prefix "ipi-oc-rpol-deviations";

  import openconfig-routing-policy { prefix oc-rpol; }
  import openconfig-bgp-policy { prefix oc-bgp-pol; }

  revision "2021-09-13" {
    description "Policy Definition name could not have space characters and have a length limitation";
  }

  revision "2021-07-29" {
    description "call-policy is not supported";
  }

  revision "2021-04-16" {
    description "install-protocol-eq is not supported";
  }

  revision "2021-02-21" {
    description "Initial revision";
  }

  deviation /oc-rpol:routing-policy/oc-rpol:policy-definitions/oc-rpol:policy-definition/oc-rpol:config/oc-rpol:name {
    deviate replace {
      type string {
        length "0 .. 63";
        pattern '[a-zA-Z0-9_]+';
      }
    }
  }

  deviation /oc-rpol:routing-policy/oc-rpol:policy-definitions/oc-rpol:policy-definition/oc-rpol:statements/oc-rpol:statement/oc-rpol:conditions/oc-rpol:config/oc-rpol:call-policy {
    deviate not-supported;
  }

  deviation /oc-rpol:routing-policy/oc-rpol:policy-definitions/oc-rpol:policy-definition/oc-rpol:statements/oc-rpol:statement/oc-rpol:conditions/oc-rpol:config/oc-rpol:install-protocol-eq {
    deviate not-supported;
  }

  deviation /oc-rpol:routing-policy/oc-rpol:defined-sets/oc-bgp-pol:bgp-defined-sets/oc-bgp-pol:ext-community-sets/oc-bgp-pol:ext-community-set/oc-bgp-pol:config/oc-bgp-pol:match-set-options {
    deviate add {
      must ".='ANY'";
    }
  }

  deviation /oc-rpol:routing-policy/oc-rpol:defined-sets/oc-bgp-pol:bgp-defined-sets/oc-bgp-pol:ext-community-sets/oc-bgp-pol:ext-community-set/oc-bgp-pol:config/oc-bgp-pol:ext-community-member {
    deviate add {
       min-elements 1;
    }
  }

  deviation /oc-rpol:routing-policy/oc-rpol:policy-definitions/oc-rpol:policy-definition/oc-rpol:statements/oc-rpol:statement/oc-rpol:config/oc-rpol:name {
    deviate replace {
      type uint32;
    }
  }
}

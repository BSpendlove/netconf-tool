/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-sys-mgmt.yang
*
*/

module ipi-sys-mgmt {

    yang-version 1.1;

    namespace   "http://www.ipinfusion.com/yang/ocnos/ipi-sys-mgmt";

    prefix "ipi-sys-mgmt";

    organization
        "IP Infusion Inc.";

    contact
        "Address: 3965 Freedom Circle, Suite 200, Santa Clara, CA 95054
         Phone: +1 408-400-1900
         E-mail: support@ipinfusion.com
         Web: http://www.ipinfusion.com/";

    description
        "sys-mgmt allows user to shutdown or reboot the device";


    revision "2021-07-30" {
        description "sys-mgmt restructured";
        reference "Initial Version";
    }



    rpc sys-shutdown {
        description "Use this RPC to shutdown the device";
        input  {
            leaf save-config  {
                type boolean;
                mandatory true;
                description "Save configuration before reboot.";
            }
        }
    }

}

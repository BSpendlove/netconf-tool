module ipi-oc-lldp-deviations {
  namespace   "http://www.ipinfusion.com/yang/ocnos/ipi-oc-lldp-deviations";
  prefix "ipi-oc-lldp-deviations";

  import openconfig-lldp { prefix oc-lldp; }

  revision "2022-04-01" {
    description "Added default value for the enabled leaf";
  }

  revision "2022-01-19" {
    description "LLDP deviations";
  }

  revision "2021-05-04" {
    description "Add 'Not-Supported' leaves";
  }

  deviation /oc-lldp:lldp/oc-lldp:config/oc-lldp:hello-timer {
    deviate not-supported;
  }

  deviation /oc-lldp:lldp/oc-lldp:config/oc-lldp:chassis-id-type {
    deviate add {
      must "(. = 'MAC_ADDRESS')" {
        error-message "Chassis ID type must be MAC_ADDRES.";
      }
    }
  }

  deviation /oc-lldp:lldp/oc-lldp:config/oc-lldp:enabled {
    deviate replace {
      default 'false';
    }
  }

  deviation /oc-lldp:lldp/oc-lldp:config/oc-lldp:system-description {
    deviate not-supported;
  }

  deviation /oc-lldp:lldp/oc-lldp:interfaces/oc-lldp:interface/oc-lldp:neighbors/oc-lldp:neighbor/oc-lldp:capabilities {
    deviate not-supported;
  }

  deviation /oc-lldp:lldp/oc-lldp:interfaces/oc-lldp:interface/oc-lldp:neighbors/oc-lldp:neighbor/oc-lldp:custom-tlvs {
    deviate not-supported;
  }

  deviation /oc-lldp:lldp/oc-lldp:config/oc-lldp:chassis-id-type {
    deviate not-supported;
  }

}

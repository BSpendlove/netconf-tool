/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-segment-routing.yang
*
*/

module ipi-segment-routing {

    yang-version 1.1;

    namespace   "http://www.ipinfusion.com/yang/ocnos/ipi-segment-routing";

    prefix "ipi-segment-routing";

    import cml-data-types {
        prefix cml-data-types;
        revision-date 2022-04-04;
    }

    import ipi-sr-types {
        prefix ipi-sr-types;
        revision-date 2021-09-03;
    }

    import ipi-interface {
        prefix ipi-interface;
        revision-date 2022-04-05;
    }

    import ietf-yang-types {
        prefix yang;
        revision-date 2013-07-15;
    }

    import ietf-inet-types {
        prefix inet;
        revision-date 2013-07-15;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "Model for managing segment-routing global configurations and state
                which includes traffic-enireening for sr as well";


    revision "2021-06-16" {
        description "Moved prefix-sid configs from ipi-if-extended module to here";
        reference " 0.4.2.";
    }

    revision "2021-04-09" {
        description "SR-Netconf-Unit-Testing-Issues";
        reference " 0.4.1.";
    }

    revision "2021-04-05" {
        description "Adding Xpath to api support";
        reference " 0.4.0.";
    }

    revision "2021-02-28" {
        description "Adding support for SR Policy runtime attributes";
        reference " 0.3.0.";
    }

    revision "2020-12-15" {
        description "Change to have data-types in lower case instead of camel case";
        reference " 0.2.0.";
    }

    revision "2020-05-26" {
        description "Initial version";
        reference " 0.1.0.";
    }

    grouping ipv4-mapping-entry-properties-config {
        description
            "ipv4 prefix mapping entry address";
        leaf start-address  {
            type  inet:ipv4-prefix;
            description "";
        } // END of start-address definition.

    } // END of ipv4-mapping-entry-properties-config definition.
    grouping mapping-entry-common-properties-config {
        description
            "common attributes for mapping entries";
        leaf start-sid  {
            type  uint32 {
                 range "0..1048575"  {
                    description "0..1048575:Starting SID-number <0-1048575>";
                 }
            }
            description "";
        } // END of start-sid definition.

        leaf range  {
            type  uint32 {
                 range "1..65535"  {
                    description "1..65535:SID-Interval <1-65535>";
                 }
            }
            description "";
        } // END of range definition.

        leaf attached  {
            type  boolean;
            description "";
        } // END of attached definition.

    } // END of mapping-entry-common-properties-config definition.
    grouping srgb-config {
        description
            "segment routing global block configuration";
        leaf start  {
            when " ../end ";
            type  uint32 {
                 range "16000..1048575"  {
                    description "16000..1048575:SRGB Starting Range";
                 }
            }
            mandatory true;
            description "";
        } // END of start definition.

        leaf end  {
            when " ../start ";
            type  uint32 {
                 range "16000..1048575"  {
                    description "16000..1048575:SRGB End Range (block size can not exceed 262143)";
                 }
            }
            mandatory true;
            description "";
        } // END of end definition.

    } // END of srgb-config definition.
    grouping segment-routing-interface-config {
        description
            "Grouping for segment-route interface configurations";
        leaf name  {
            type  leafref {
                path  "/ipi-interface:interfaces/ipi-interface:interface/ipi-interface:name";
            }
            description "Reference to interface name";
        } // END of name definition.

    } // END of segment-routing-interface-config definition.
    grouping prefix-segment-config {
        description
            "Grouping for MPLS segment-route Prefix configurations";
        leaf sid-absolute  {
            type  uint32 {
                 range "16000..1048575"  {
                    description "16000..1048575:SID Absolute-value";
                 }
            }
            description "This attribute is used to configure Segment Route Prefix SID absolute
                        value";
        } // END of sid-absolute definition.

        leaf sid-index  {
            type  uint32 {
                 range "0..1048575"  {
                    description "0..1048575:SID Index-value";
                 }
            }
            description "This attribute is used to configure Segment Route Prefix SID
                        index-value";
        } // END of sid-index definition.

        leaf exp-null  {
            type  ipi-sr-types:if_sr_prefix_flag_t;
            description "This attribute describes except Null";
        } // END of exp-null definition.

        leaf n-flag-clear  {
            type  ipi-sr-types:if_sr_n_flag_clear_t;
            description "This attribute is used to set n-flag-clear";
        } // END of n-flag-clear definition.

    } // END of prefix-segment-config definition.
    grouping prefer-sr-config {
        description
            "preference configuration for segment routing label over LDP label";
        leaf enable-preference  {
            type  empty;
            description "preference for segment routing label over LDP";
        } // END of enable-preference definition.

    } // END of prefer-sr-config definition.
    grouping srms-preference-value-config {
        description
            "preference configuration for segment routing mapping server";
        leaf preference  {
            type  uint8 {
                 range "1..255"  {
                    description "1..255:Preference value <1-255>";
                 }
            }
            description "preference for segment routing mapping server";
        } // END of preference definition.

    } // END of srms-preference-value-config definition.
    grouping prefix-sid-config {
        description
            "Prefix-sid configurations";
        leaf prefix  {
            type  inet:ip-prefix;
            description "connected prefix for prefix-sid";
        } // END of prefix definition.

        uses prefix-sid-attributes-config;
    } // END of prefix-sid-config definition.
    grouping prefix-sid-attributes-config {
        description
            "Prefix-sid attributes";
        leaf start-sid  {
            type  uint32;
            description "Value associated with prefix. The value must be
                        interpreted in the context of value-type.";
        } // END of start-sid definition.

    } // END of prefix-sid-attributes-config definition.
    grouping sid-value-type-config {
        description
            "This grouping defines how SID value is expressed";
        leaf value-type  {
            type  ipi-sr-types:sr_sid_value_type_t;
            description "Defines how the SID value is expressed.";
        } // END of value-type definition.

    } // END of sid-value-type-config definition.
    grouping sr-config {
        description
            "config attribute for frr for SR";
        leaf enable  {
            type  empty;
            mandatory true;
            description "";
        } // END of enable definition.

    } // END of sr-config definition.
    grouping te-config {
        description
            "config attribute for traffic-engineering for SR Policies";
        leaf enable  {
            type  empty;
            mandatory true;
            description "";
        } // END of enable definition.

    } // END of te-config definition.
    grouping prefix-sid-map-ipv4-config {
        description
            "config attribute for prefix-sid-map-ipv4";
        leaf enable  {
            type  empty;
            mandatory true;
            description "To enable ipv4 mapping server configuration";
        } // END of enable definition.

    } // END of prefix-sid-map-ipv4-config definition.
    grouping frr-config {
        description
            "config attribute for frr for SR Policies";
        leaf fast-reroute-enable  {
            type  empty;
            description "Enable fast reroute for traffic engineering polices";
        } // END of fast-reroute-enable definition.

    } // END of frr-config definition.
    grouping segment-properties-common-config {
        description
            "Common properties of segment which includes it's index value and it's
                        type.";
        leaf segment-index  {
            type  uint32 {
                 range "1..65535"  {
                    description "1..65535:Index number";
                 }
            }
            description "Index of the segment through which it can be modified or unconfigured";
        } // END of segment-index definition.

        leaf type  {
            type  ipi-sr-types:srte_segment_type_t;
            description "Type of the segment";
        } // END of type definition.

    } // END of segment-properties-common-config definition.
    grouping segment-type-1-properties-config {
        description
            "grouping for the properties of segment type 1";
        leaf sid-value  {
            type  uint32 {
                 range "0..1048575"  {
                    description "0..1048575:Label value";
                 }
            }
            description "MPLS label value";
        } // END of sid-value definition.

    } // END of segment-type-1-properties-config definition.
    grouping attributes-config {
        description
            "Grouping containing attributes applicable to all SR policies";
        container attributes {
            description
                "Attributes applicable to SR policies";
            uses segment-lists-config;
        } // END of attributes-container definition.
    } // END of attributes-config definition.
    grouping segment-list-config {
        description
            "config attributes for segment list";
        leaf list-name  {
            type  string {
                length "1..1965";
                pattern "[^?' =,>|]+";
            }
            description "Segment-list name";
        } // END of list-name definition.

    } // END of segment-list-config definition.
    grouping segment-lists-config {
        description
            "Segment lists grouping";
        container segment-lists {
            when " /ipi-segment-routing:segment-routing/ipi-segment-routing:traffic-engineering/ipi-segment-routing:config/ipi-segment-routing:enable ";
            if-feature feature-list:HAVE_SR_POLICY;
            description
                "Segment-lists properties";

            list segment-list {
                key "list-name";
                description
                    "Properties of a segment list";
                leaf list-name  {
                    type  leafref {
                        path  "../config/list-name";
                    }
                    description "Segment-list name";
                } // END of list-name definition.

                container config {
                    description
                        "Config parameters for segment-list configuration";
                    uses segment-list-config;
                } // END of config-container definition.
                container state {
                    config false;
                    description
                        "";
                    uses segment-list-config;
                } // END of state-container definition.
                container segments {
                    description
                        "Segments for given segment list";

                    list segment {
                        key "segment-index type";
                        description
                            "Configure a segment at given index";
                        leaf segment-index  {
                            type  leafref {
                                path  "../config/segment-index";
                            }
                            description "Index of the segment through which it can be modified or unconfigured";
                        } // END of segment-index definition.

                        leaf type  {
                            type  leafref {
                                path  "../config/type";
                            }
                            description "Type of the segment";
                        } // END of type definition.

                        container config {
                            description
                                "Contains config parameters for configuring segment index and type";
                            uses segment-properties-common-config;
                        } // END of config-container definition.
                        container state {
                            config false;
                            description
                                "Contains operational information about segment index and type";
                            uses segment-properties-common-config;
                        } // END of state-container definition.
                        container segment-type-1 {
                            description
                                "Segment declared by MPLS label";
                            container config {
                                description
                                    "Contains parameters to configure segment-type-1";
                                uses segment-type-1-properties-config;
                            } // END of config-container definition.
                            container state {
                                config false;
                                description
                                    "Contains operational information regarding segment-type-1";
                                uses segment-type-1-properties-config;
                            } // END of state-container definition.
                        } // END of segment-type-1-container definition.
                    } // End of segment-list
                } // END of segments-container definition.
            } // End of segment-list-list
        } // END of segment-lists-container definition.
    } // END of segment-lists-config definition.
    grouping policies-config {
        description
            "SR policy grouping";
        container policies {
            when " /ipi-segment-routing:segment-routing/ipi-segment-routing:traffic-engineering/ipi-segment-routing:config/ipi-segment-routing:enable ";
            if-feature feature-list:HAVE_SR_POLICY;
            description
                "SR Policy container";

            list policy {
                key "name";
                description
                    "SR Policy properties";
                leaf name  {
                    type  leafref {
                        path  "../config/name";
                    }
                    description "User friendly name of the SR Policy";
                } // END of name definition.


                list policy-key {
                    key "color end-point";
                    description
                        "SR Policy key";
                    leaf color  {
                        type  leafref {
                            path  "../config/color";
                        }
                        description "Color associated with the policy";
                    } // END of color definition.

                    leaf end-point  {
                        type  leafref {
                            path  "../config/end-point";
                        }
                        description "Policy end point IP address";
                    } // END of end-point definition.

                    container config {
                        description
                            "SR policy config container";
                        uses policy-key-properties-config;
                    } // END of config-container definition.
                    container state {
                        config false;
                        description
                            "SR policy state container";
                        uses policy-key-properties-config;
                    } // END of state-container definition.
                } // End of policy-key-list
                container config {
                    description
                        "SR policy config container";
                    uses policy-properties-config;
                } // END of config-container definition.
                container candidate-paths {
                    description
                        "SR policy candidate path(s)";

                    list candidate-path {
                        key "discriminator protocol-origin originator";
                        description
                            "SR policy Candidate path(s) list entry";
                        leaf discriminator  {
                            type  leafref {
                                path  "../config/discriminator";
                            }
                            description "Candidate path distinguisher, it's taken as a unique
                                        identifier for a Local candidate path";
                        } // END of discriminator definition.

                        leaf protocol-origin  {
                            type  leafref {
                                path  "../config/protocol-origin";
                            }
                            description "Instantiation mechanism used to create the candidate  path";
                        } // END of protocol-origin definition.

                        leaf originator  {
                            type  leafref {
                                path  "../config/originator";
                            }
                            description "Identifier (concatenation of ASN and node-address) of
                                        the node that signalled/instantiated the candidate
                                        path on headend";
                        } // END of originator definition.

                        container config {
                            description
                                "SR policy config container";
                            uses candidate-paths-properties-config;
                        } // END of config-container definition.
                        container state {
                            config false;
                            description
                                "SR policy candidate path table";
                            uses candidate-paths-properties-config;
                            uses candidate-paths-properties-state;
                        } // END of state-container definition.
                        container forwarding-paths {
                            config false;
                            description
                                "Top level container for SR Policy candidate forwarding paths";
                            container forwarding-path {
                                config false;
                                description
                                    "SR policy candidate path forwarding path";
                                container state {
                                    config false;
                                    description
                                        "SR policy forwarding path table";
                                    uses forwarding-path-state;
                                } // END of state-container definition.
                                container label-stack {
                                    config false;
                                    description
                                        "SR policy forwarding path label stack";
                                    container labels {
                                        config false;
                                        description
                                            "SR policy forwarding path labels";
                                        container state {
                                            config false;
                                            description
                                                "SR policy label stack table";
                                            uses label-stack-state;
                                        } // END of state-container definition.
                                    } // END of labels-container definition.
                                } // END of label-stack-container definition.
                            } // END of forwarding-path-container definition.
                        } // END of forwarding-paths-container definition.
                        uses candidate-path-types-config;
                    } // End of candidate-path-list
                } // END of candidate-paths-container definition.
                container state {
                    config false;
                    description
                        "SR policy state container";
                    container statistics {
                        config false;
                        description
                            "Segment Routing Policy packet stats";
                        uses sr-policy-stats-state;
                    } // END of statistics-container definition.
                    uses policy-properties-config;
                    uses policy-properties-state;
                } // END of state-container definition.
            } // End of policy-list
        } // END of policies-container definition.
    } // END of policies-config definition.
    grouping policy-key-properties-config {
        description
            "SR Policy configuration parameters grouping";
        leaf color  {
            type  uint32 {
                 range "1..4294967295"  {
                    description "1..4294967295:color value";
                 }
            }
            description "Color associated with the policy";
        } // END of color definition.

        leaf end-point  {
            type  inet:ipv4-address;
            description "Policy end point IP address";
        } // END of end-point definition.

    } // END of policy-key-properties-config definition.
    grouping policy-properties-config {
        description
            "SR Policy configuration parameters grouping";
        leaf name  {
            type  string {
                length "1..1965";
                pattern "[^?' =,>|]+";
            }
            description "User friendly name of the SR Policy";
        } // END of name definition.

        leaf admin-state  {
            type  empty;
            description "SR policy administrative state, true for enabled, false for disabled";
        } // END of admin-state definition.

        leaf explicit-null  {
            type  ipi-sr-types:srte_explicite_null_type_t;
            description "To set explicit null behaviour for the policy";
        } // END of explicit-null definition.

        leaf cspf-retry-limit  {
            type  uint32 {
                 range "1..65535"  {
                    description "1..65535:Number of times CSPF should retry";
                 }
            }
            description "Limit on the number of times a dynamic candidate path will retry to
                        calculate segment-list";
        } // END of cspf-retry-limit definition.

        leaf cspf-retry-interval  {
            type  uint32 {
                 range "1..600"  {
                    description "1..600:Time in seconds between successive retries";
                 }
            }
            description "Interval between two successive retries for calculating
                        segment list of a dynamic candidate path using CSPF";
        } // END of cspf-retry-interval definition.

        leaf pce-lsp-delegate  {
            if-feature feature-list:HAVE_PCEP_SR;
            type  empty;
            description "To delegate all the configured candidate path of policy to PCE
                        controller";
        } // END of pce-lsp-delegate definition.

        leaf pce-state-report  {
            if-feature feature-list:HAVE_PCEP_SR;
            type  empty;
            description "To only report all the configured candidate path of policy to PCE
                        controller";
        } // END of pce-state-report definition.

        leaf pce-entity-id  {
            if-feature feature-list:HAVE_PCEP_SR;
            type  uint32 {
                 range "1..255"  {
                    description "1..255:PCE Entity ID";
                 }
            }
            description "Entity Id of PCEP entity to which this policy should be
                        queried/reported/delegated";
        } // END of pce-entity-id definition.

        uses bsid-properties-config;
    } // END of policy-properties-config definition.
    grouping bsid-properties-config {
        description
            "SR Policy BSID properties grouping";
        leaf bsid-value  {
            type  uint32 {
                 range "16..15999"  {
                    description "16..15999:MPLS label";
                 }
            }
            description "configurable value for static binding sid";
        } // END of bsid-value definition.

    } // END of bsid-properties-config definition.
    grouping policy-properties-state {
        description
            "SR Policy BSID properties grouping";
        leaf oper-state  {
            type  ipi-sr-types:srte_policy_oper_state_t;
            description "SR policy operational state";
        } // END of oper-state definition.

        leaf transition-count  {
            type  uint32;
            description "Indicates number of up/down transitions";
        } // END of transition-count definition.

        leaf up-time  {
            type  yang:date-and-time {
                pattern "\\d{4}-\\d{2}-\\d{2}T\\d{2}:\\d{2}:\\d{2}(\\.\\d+)?(Z|[\\+\\-]\\d{2}:\\d{2})";
                }
                description "Policy up time in seconds";
            } // END of up-time definition.

            leaf down-time  {
                type  yang:date-and-time {
                    pattern "\\d{4}-\\d{2}-\\d{2}T\\d{2}:\\d{2}:\\d{2}(\\.\\d+)?(Z|[\\+\\-]\\d{2}:\\d{2})";
                    }
                    description "Policy down time in seconds";
                } // END of down-time definition.

                leaf bsid-alloc-mode  {
                    type  string {
                        length "1..1965";
                        pattern "[^?' =,>|]+";
                    }
                    description "SR Policy Binding SID alloc mode";
                } // END of bsid-alloc-mode definition.

                leaf bsid-oper-state  {
                    type  ipi-sr-types:sr_policy_bsid_oper_state;
                    description "SR Policy Binding SID operational state";
                } // END of bsid-oper-state definition.

    } // END of policy-properties-state definition.
    grouping sr-policy-stats-state {
        description
            "Segment Routing Policy packet stats";
        leaf tx-bytes  {
            type  uint64;
            description "SR Policy statistics Tx Bytes";
        } // END of tx-bytes definition.

        leaf rx-bytes  {
            type  uint64;
            description "SR Policy statistics Rx Bytes";
        } // END of rx-bytes definition.

        leaf tx-packets  {
            type  uint64;
            description "SR Policy statistics Tx Packets";
        } // END of tx-packets definition.

        leaf rx-packets  {
            type  uint64;
            description "SR Policy statistics Rx Packets";
        } // END of rx-packets definition.

    } // END of sr-policy-stats-state definition.
    grouping candidate-paths-properties-config {
        description
            "SR Policy candidate path grouping";
        leaf discriminator  {
            type  uint32 {
                 range "1..65535"  {
                    description "1..65535:Identifier value for candidate path";
                 }
            }
            description "Candidate path distinguisher, it's taken as a unique
                        identifier for a Local candidate path";
        } // END of discriminator definition.

        leaf protocol-origin  {
            type  ipi-sr-types:srte_protocol_origin_type_type_t;
            default "local";
            description "Instantiation mechanism used to create the candidate  path";
        } // END of protocol-origin definition.

        leaf originator  {
            type  string {
                length "0..1965";
                pattern "[^?' =,>|]*";
            }
            description "Identifier (concatenation of ASN and node-address) of
                        the node that signalled/instantiated the candidate
                        path on headend";
        } // END of originator definition.

        leaf preference  {
            type  uint32 {
                 range "1..65535"  {
                    description "1..65535:Preference value for candidate path";
                 }
            }
            default "100";
            description "Candidate path preference";
        } // END of preference definition.

    } // END of candidate-paths-properties-config definition.
    grouping candidate-paths-properties-state {
        description
            "SR Policy candidate path state attribute grouping";
        leaf is-valid  {
            type  boolean;
            description "Specifies the state of candidate path";
        } // END of is-valid definition.

        leaf non-selection-reason  {
            type  string {
                length "1..1965";
                pattern "[^?' =,>|]+";
            }
            description "Specifies the inactive reason for candidate path";
        } // END of non-selection-reason definition.

        leaf is-best-candidate-path  {
            type  boolean;
            description "Specifies the whether it is best candidate path";
        } // END of is-best-candidate-path definition.

    } // END of candidate-paths-properties-state definition.
    grouping forwarding-path-state {
        description
            "Forwarding paths grouping";
        leaf path-id  {
            type  uint8;
            description "Specifies the forwarding path ID";
        } // END of path-id definition.

        leaf next-hop-address  {
            type  inet:ip-address;
            description "Specifies the IP address of next hop";
        } // END of next-hop-address definition.

        leaf outgoing-interface  {
            type  string {
                length "1..1965";
                pattern "[^?' =,>|]+";
            }
            description "Specifies the outgoing interface";
        } // END of outgoing-interface definition.

        leaf path-type  {
            type  string {
                length "1..1965";
                pattern "[^?' =,>|]+";
            }
            description "Specifies the path type";
        } // END of path-type definition.

    } // END of forwarding-path-state definition.
    grouping label-stack-state {
        description
            "Label stack grouping";
        leaf label  {
            type  string {
                length "1..1965";
                pattern "[^?' =,>|]+";
            }
            description "Specifies the label";
        } // END of label definition.

    } // END of label-stack-state definition.
    grouping candidate-path-types-config {
        description
            "Candidate path type grouping";
        container dynamic {
            if-feature feature-list:HAVE_SR_POLICY;
            description
                "Candidate path with dynamic computed segment-list";
            container config {
                description
                    "Dynamic CP config container";
                uses dynamic-path-properties-config;
            } // END of config-container definition.
            container state {
                config false;
                description
                    "Dynamic CP state container";
                uses dynamic-path-properties-config;
            } // END of state-container definition.
            container constraints {
                when " /ipi-segment-routing:segment-routing/ipi-segment-routing:traffic-engineering/ipi-segment-routing:policies/ipi-segment-routing:policy/ipi-segment-routing:candidate-paths/ipi-segment-routing:candidate-path/ipi-segment-routing:dynamic/ipi-segment-routing:config/ipi-segment-routing:isis  or /ipi-segment-routing:segment-routing/ipi-segment-routing:traffic-engineering/ipi-segment-routing:policies/ipi-segment-routing:policy/ipi-segment-routing:candidate-paths/ipi-segment-routing:candidate-path/ipi-segment-routing:dynamic/ipi-segment-routing:config/ipi-segment-routing:ospf  or /ipi-segment-routing:segment-routing/ipi-segment-routing:traffic-engineering/ipi-segment-routing:policies/ipi-segment-routing:policy/ipi-segment-routing:candidate-paths/ipi-segment-routing:candidate-path/ipi-segment-routing:dynamic/ipi-segment-routing:config/ipi-segment-routing:pcep ";
                // when " ipi-segment-routing:segment-routing/traffic-engineering/policies/policy/candidate-paths/candidate-path/dynamic/constraints/config/enable ";
                description
                    "constraints for candidate path which needs to be satisfied by
                            computation engine when calculating a segment-list for the cp";

                list bounds {
                    key "metric-type";
                    max-elements 1;
                    description
                        "Upper-bound constraints on the computed dynamic path";
                    leaf metric-type  {
                        type  leafref {
                            path  "../config/metric-type";
                        }
                        description "Metric type can be IGP or TE";
                    } // END of metric-type definition.

                    container config {
                        description
                            "Bounds config container";
                        uses bounds-config;
                    } // END of config-container definition.
                    container state {
                        config false;
                        description
                            "Bounds State container";
                        uses bounds-config;
                    } // END of state-container definition.
                } // End of bounds-list
                container config {
                    presence "yes";
                    description
                        "constraint config container";
                    uses constraints-config;
                } // END of config-container definition.
                container state {
                    config false;
                    description
                        "constraint state container";
                    uses constraints-config;
                } // END of state-container definition.
                container admin-groups {
                    when " /ipi-segment-routing:segment-routing/ipi-segment-routing:traffic-engineering/ipi-segment-routing:policies/ipi-segment-routing:policy/ipi-segment-routing:candidate-paths/ipi-segment-routing:candidate-path/ipi-segment-routing:dynamic/ipi-segment-routing:constraints ";
                    if-feature feature-list:HAVE_SR_POLICY;
                    description
                        "CP constraint admin-group";

                    list admin-group {
                        if-feature feature-list:HAVE_SR_POLICY;
                        key "admin-group-name";
                        description
                            "list of affinity admin group";
                        leaf admin-group-name  {
                            type  leafref {
                                path  "../config/admin-group-name";
                            }
                            description "admin group name";
                        } // END of admin-group-name definition.

                        container config {
                            description
                                "configuration container for affinity admin group";
                            uses admin-group-config;
                        } // END of config-container definition.
                        container state {
                            config false;
                            description
                                "state container for admin group";
                            uses admin-group-config;
                        } // END of state-container definition.
                    } // End of admin-group-list
                } // END of admin-groups-container definition.
                container ip {
                    description
                        "IP constraints to be used for dynamic candidate path";

                    list include-hop {
                        key "address";
                        description
                            "All the ip constriants should be  included for the path computation";
                        leaf address  {
                            type  leafref {
                                path  "../config/address";
                            }
                            description "Hop address which needs toincluded in the LSP";
                        } // END of address definition.

                        container config {
                            description
                                "include-hop config container";
                            uses include-ip-constraints-config;
                        } // END of config-container definition.
                        container state {
                            description
                                "include-hop state container";
                            uses include-ip-constraints-config;
                        } // END of state-container definition.
                    } // End of include-hop-list
                } // END of ip-container definition.
            } // END of constraints-container definition.
        } // END of dynamic-container definition.
        container explicit {
            description
                "Candidate path with explicitly defined set of segment-list";
            uses explicit-path-properties;
        } // END of explicit-container definition.
    } // END of candidate-path-types-config definition.
    grouping include-ip-constraints-config {
        description
            "Ip addresses to be        included as constraints for the dynamic path";
        leaf address  {
            type  inet:ipv4-address;
            description "Hop address which needs toincluded in the LSP";
        } // END of address definition.

        leaf type  {
            type  ipi-sr-types:srte_ip_constraint_hop_type_t;
            description "Type of the constraints whether it is node or loose or it is a link or
                        strict, It is highly recomeneded to use strict fro link constraint";
        } // END of type definition.

    } // END of include-ip-constraints-config definition.
    grouping bounds-config {
        description
            "various bound constraints for the dynamic candidate path";
        leaf metric-type  {
            type  ipi-sr-types:srte_cp_metric_type_t;
            description "Metric type to be used for path computation for this dynamic cp";
        } // END of metric-type definition.

        leaf bound  {
            when " ../metric-type ";
            type  uint32 {
                 range "1..4294967295"  {
                    description "1..4294967295:Maximum allowed metric value";
                 }
            }
            description "Path is invalid if its metric exceeds this value,
                        If no value is specified";
        } // END of bound definition.

        leaf segment-bound  {
            type  uint32;
            description "Path is invalid if it has more segments than this value";
        } // END of segment-bound definition.

    } // END of bounds-config definition.
    grouping affinity-config {
        description
            "affinity constraints for the dynamic candidate path";
        leaf-list exclude-any  {
            type  string {
                length "1..1965";
                pattern "[^?' =,>|]+";
            }
            description "The link is excluded if it has any of these affinities.";
        } // END of exclude-any definition.

        leaf-list include-any  {
            type  string {
                length "1..1965";
                pattern "[^?' =,>|]+";
            }
            description "The link is accepted if it has any of these affinities.";
        } // END of include-any definition.

        leaf-list include-all  {
            type  string {
                length "1..1965";
                pattern "[^?' =,>|]+";
            }
            description "The link is accepted if it has all these affinities.";
        } // END of include-all definition.

    } // END of affinity-config definition.
    grouping dynamic-path-properties-config {
        description
            "Dynamic path properties of the candidate path";
        leaf pcep  {
            if-feature feature-list:HAVE_PCEP_SR;
            type  empty;
            description "";
        } // END of pcep definition.

        leaf isis  {
            type  string {
                length "0..1965";
                pattern "[^?' =,>|]*";
            }
            default "";
            description "";
        } // END of isis definition.

        leaf ospf  {
            type  int32 {
                 range "-1..65535"  {
                    description "-1..65535:OSPF process id";
                 }
            }
            description "";
        } // END of ospf definition.

    } // END of dynamic-path-properties-config definition.
    grouping explicit-path-properties {
        description
            "Dynamic path properties of the candidate path";
        container segment-lists {
            description
                "Path segment list(s) properties";

            list segment-list {
                key "list-name";
                description
                    "SR policy candidate path segment lists";
                leaf list-name  {
                    type  leafref {
                        path  "../config/list-name";
                    }
                    description "Reference to segment-list name";
                } // END of list-name definition.

                container config {
                    description
                        "";
                    uses segment-list-config;
                } // END of config-container definition.
            } // End of segment-list-list
        } // END of segment-lists-container definition.
    } // END of explicit-path-properties definition.
    grouping constraints-config {
        description
            "Configuration to change to constraints mode";
        leaf enable  {
            type  empty;
            mandatory true;
            description "Enable constraints for the candidate path";
        } // END of enable definition.

    } // END of constraints-config definition.
    grouping admin-group-config {
        description
            "configuration parameters for admin group";
        leaf affinity-type  {
            type  ipi-sr-types:sr_te_admin_group_type_t;
            description "Use this attribute to configure the type is include-any or include-all
                        or exclude-any";
        } // END of affinity-type definition.

        leaf admin-group-name  {
            type  string {
                length "1..1965";
                pattern "[^?' =,>|]+";
            }
            description "Affinity admin-group name";
        } // END of admin-group-name definition.

    } // END of admin-group-config definition.
    grouping policy-debug-config {
        description
            "Configuration data related to debugging policy";
        leaf enable-debug  {
            type  ipi-sr-types:sr_te_debug_t;
            description "This attribute is used to enable/disable SR Policy debug logs";
        } // END of enable-debug definition.

    } // END of policy-debug-config definition.
    grouping debug-policy-config {
        description
            "debug related attributes for sr policy";
        container debug {
            if-feature feature-list:HAVE_SR_POLICY;
            description
                "enable/disable debug for sr-policy";
            container config {
                description
                    "Configuration data for debugging parameters";
                uses policy-debug-config;
            } // END of config-container definition.
            container state {
                config false;
                description
                    "Operational data for debugging parameters";
                uses policy-debug-config;
            } // END of state-container definition.
        } // END of debug-container definition.
    } // END of debug-policy-config definition.
    grouping srms-ipv4-prefix-sid-map-state {
        description
            "SRMS prefix-sid-map detail";
        leaf start-prefix  {
            type  cml-data-types:cml_ip_prefix_addr_t;
            description "SR MS prefix-sid-map Start Address";
        } // END of start-prefix definition.

        leaf start-sid-index  {
            type  uint16;
            description "Start SID Index";
        } // END of start-sid-index definition.

        leaf range  {
            type  uint16;
            description "range";
        } // END of range definition.

        leaf end-prefix  {
            type  cml-data-types:cml_ip_prefix_addr_t;
            description "SR MS prefix-sid-map End Address";
        } // END of end-prefix definition.

        leaf end-sid-index  {
            type  uint16;
            description "Last SID Index";
        } // END of end-sid-index definition.

        leaf attached  {
            type  empty;
            description "SR MS attachedd";
        } // END of attached definition.

        leaf preference  {
            type  uint8;
            description "SR map table entry SRMS pref";
        } // END of preference definition.

    } // END of srms-ipv4-prefix-sid-map-state definition.

    grouping  segment-routing-grouping {
    description
        "This defines a YANG data model for segment routing MPLS and TE
                configuration and operation. This document does not define the IGP
                extensions to support segment routing";
    container segment-routing {
        if-feature feature-list:HAVE_SR_MPLS;
        description
            "This defines a YANG data model for segment routing MPLS and TE
                    configuration and operation. This document does not define the IGP
                    extensions to support segment routing";
        container config {
            presence "yes";
            description
                "segment-routing configuration container,         enables global
                        configuration of segment-routing and allows to configure
                        various SR related CLIs";
            uses sr-config;
        } // END of config-container definition.
        container state {
            config false;
            description
                "segment-routing state container describes segment-routing state";
            uses sr-config;
        } // END of state-container definition.
        container interfaces {
            description
                "Top level container for interfaces, including configuration and state
                        data";

            list interface {
            // when " !ipi-if-aggregate:member-aggregation ";
                key "name";
                description
                    "This list defines global SR interface configuration and state
                                information.";
                leaf name  {
                    type  leafref {
                        path  "../config/name";
                    }
                    description "Reference to interface name";
                } // END of name definition.

                container config {
                    description
                        "Configuration data for segment-routing interface name";
                    uses segment-routing-interface-config;
                } // END of config-container definition.
                container prefix-segment {
                    when " /ipi-interface:interfaces/ipi-interface:interface/ipi-interface:config/ipi-interface:enable-switchport != '1' ";
                    if-feature feature-list:HAVE_SR_MPLS;
                    description
                        "MPLS segment-route Prefix";
                    container config {
                        when " ../config/sid-index or ../config/sid-absolute ";
                        description
                            "Configuration data for segment-route prefix module";
                        uses prefix-segment-config;
                    } // END of config-container definition.
                    container state {
                        config false;
                        description
                            "Operational state data for segment-route prefix module";
                        uses prefix-segment-config;
                    } // END of state-container definition.
                } // END of prefix-segment-container definition.
            } // End of interface-list
        } // END of interfaces-container definition.
        container sr-mpls {
            when " /ipi-segment-routing:segment-routing/ipi-segment-routing:config/ipi-segment-routing:enable ";
            if-feature feature-list:HAVE_SR_MPLS;
            description
                "SR MPLS data plane global configuration and operational state";
            container sr-prefer-over-ldp {
                description
                    "to prefer segment-routing labels over LDP labels";
                container config {
                    description
                        "config attribute for preferring sr-label over LDP";
                    uses prefer-sr-config;
                } // END of config-container definition.
                container state {
                    config false;
                    description
                        "State attribute to describe preference of sr-label over LDP";
                    uses prefer-sr-config;
                } // END of state-container definition.
            } // END of sr-prefer-over-ldp-container definition.
            container bindings {
                description
                    "prefix to sid bindings";
                container mapping-server {
                    description
                        "Configuration and state information of mapping-server entries.";
                    container config {
                        presence "yes";
                        description
                            "config parameters for mapping-server entries";
                        leaf enable  {
                            type  empty;
                            mandatory true;
                            description "To enable mapping server configuration";
                        } // END of enable definition.

                    } // END of config-container definition.
                    container state {
                        config false;
                        description
                            "Operational parameters for mapping-server entries";
                        leaf enable  {
                            type  empty;
                            mandatory true;
                            description "To enable mapping server configuration";
                        } // END of enable definition.

                    } // END of state-container definition.
                    container srms-preferenece {
                        when " /ipi-segment-routing:segment-routing/ipi-segment-routing:sr-mpls/ipi-segment-routing:bindings/ipi-segment-routing:mapping-server/ipi-segment-routing:config/ipi-segment-routing:enable ";
                        description
                            "The SRMS preference TLV is               used to advertise a
                                    preference associated with the node that acts               as an SR
                                    Mapping Server";
                        container config {
                            description
                                "container used to configure preference value associated with node that
                                        acts as an Mapping server";
                            uses srms-preference-value-config;
                        } // END of config-container definition.
                        container state {
                            config false;
                            description
                                "Operational parameters of SRMS preference TLV";
                            uses srms-preference-value-config;
                        } // END of state-container definition.
                    } // END of srms-preferenece-container definition.
                    container prefix-sid-map-ipv4 {
                        when " /ipi-segment-routing:segment-routing/ipi-segment-routing:sr-mpls/ipi-segment-routing:bindings/ipi-segment-routing:mapping-server/ipi-segment-routing:config/ipi-segment-routing:enable ";
                        description
                            "mapping-server entries.";

                        list mapping-entry {
                            key "start-address start-sid";
                            description
                                "This objectlist contains config and state parameters for mapping
                                            entries";
                            leaf start-address  {
                                type  leafref {
                                    path  "../config/start-address";
                                }
                                description "connected prefix for prefix-sid";
                            } // END of start-address definition.

                            leaf start-sid  {
                                type  leafref {
                                    path  "../config/start-sid";
                                }
                                description "";
                            } // END of start-sid definition.

                            container config {
                                description
                                    "this container contains configuration parameters for mapping entries";
                                uses ipv4-mapping-entry-properties-config;
                                uses mapping-entry-common-properties-config;
                            } // END of config-container definition.
                            container state {
                                config false;
                                description
                                    "this container contains operational parameters for mapping entries";
                                uses ipv4-mapping-entry-properties-config;
                                uses mapping-entry-common-properties-config;
                            } // END of state-container definition.
                            container ipv4-table {
                                config false;
                                description
                                    "IPv4 SR Mapping Table Attributes";
                                container state {
                                    config false;
                                    description
                                        "IPv4 SR Mapping-Server Table";
                                    uses srms-ipv4-prefix-sid-map-state;
                                } // END of state-container definition.
                            } // END of ipv4-table-container definition.
                        } // End of mapping-entry-list
                        container config {
                            presence "yes";
                            description
                                "Config parameters to enable mapping server configuration";
                            leaf enable  {
                                type  empty;
                                mandatory true;
                                description "To enable ipv4 mapping server configuration";
                            } // END of enable definition.

                        } // END of config-container definition.
                        container state {
                            config false;
                            description
                                "Operational information of mapping server";
                            leaf enable  {
                                type  empty;
                                mandatory true;
                                description "To enable ipv4 mapping server configuration";
                            } // END of enable definition.

                        } // END of state-container definition.
                    } // END of prefix-sid-map-ipv4-container definition.
                } // END of mapping-server-container definition.
            } // END of bindings-container definition.
            container global-block {
                if-feature feature-list:HAVE_SR_MPLS;
                description
                    "Segment routing Global block";
                container config {
                    presence "yes";
                    description
                        "Configurable parameters for SRGB";
                    uses srgb-config;
                } // END of config-container definition.
                container state {
                    config false;
                    description
                        "Operational parameters for SRGB";
                    uses srgb-config;
                } // END of state-container definition.
            } // END of global-block-container definition.
        } // END of sr-mpls-container definition.
        container traffic-engineering {
            when " /ipi-segment-routing:segment-routing/ipi-segment-routing:config/ipi-segment-routing:enable ";
            if-feature feature-list:HAVE_SR_POLICY;
            description
                "Traffic-engineering container for segment routing";
            container config {
                presence "yes";
                description
                    "Segment routing traffic engineering configuration and other CLIs
                            inside traffic enginnering";
                uses frr-config;
                uses te-config;
            } // END of config-container definition.
            container state {
                config false;
                description
                    "Segment routing traffic engineering runtime parameters";
                uses frr-config;
                uses te-config;
            } // END of state-container definition.
            uses attributes-config;
            uses policies-config;
        } // END of traffic-engineering-container definition.
        uses debug-policy-config;
    } // END of segment-routing-container definition.
    } // END of segment-routing-grouping definition.

    uses segment-routing-grouping;

    rpc debug-sr-policy {
        description "Enable debugging functions of sr-policy";
        input  {
            leaf enable-debug  {
                type ipi-sr-types:sr_te_debug_t;
                mandatory true;
                description "";
            }
        }
    }

    rpc undebug-sr-policy {
        description "Disable debugging functions of SR Policy";
        input  {
            leaf enable-debug  {
                type ipi-sr-types:sr_te_debug_t;
                mandatory true;
                description "";
            }
        }
    }

    notification sr-policy-oper-state-down {

        description "This notification is sent when SR policy oper-state goes down.";

        // severity "MAJOR";
        // eventClass "STATE";
        leaf name {
            type  string;
        description
            "User friendly name of the SR Policy";
        }

        leaf oper-state {
            type ipi-sr-types:srte_policy_oper_state_t;
        description
            "SR policy operational state";
        }
    }

    notification sr-policy-oper-state-up {

        description "This notification is sent when SR policy oper-state goes up.";

        // severity "MAJOR";
        // eventClass "STATE";
        leaf name {
            type  string;
        description
            "User friendly name of the SR Policy";
        }

        leaf oper-state {
            type ipi-sr-types:srte_policy_oper_state_t;
        description
            "SR policy operational state";
        }
    }

    notification sr-policy-cp-active {

        description "This notification is sent when SR policy candidate-path active.";

        // severity "MAJOR";
        // eventClass "STATE";
        leaf discriminator {
            type  uint32;
        description
            "Candidate path distinguisher, it's taken as a unique
                    identifier for a Local candidate path";
        }

        leaf protocol-origin {
            type ipi-sr-types:srte_protocol_origin_type_type_t;
        description
            "Instantiation mechanism used to create the candidate  path";
        }

        leaf originator {
            type  string;
        description
            "Identifier (concatenation of ASN and node-address) of
                    the node that signalled/instantiated the candidate
                    path on headend";
        }

        leaf name {
            type  string;
        description
            "User friendly name of the SR Policy";
        }

        leaf is-valid {
            type  boolean;
        description
            "Specifies the state of candidate path";
        }
    }

    notification sr-policy-cp-inactive {

        description "This notification is sent when SR policy candidate-patj in-active.";

        // severity "MAJOR";
        // eventClass "STATE";
        leaf discriminator {
            type  uint32;
        description
            "Candidate path distinguisher, it's taken as a unique
                    identifier for a Local candidate path";
        }

        leaf protocol-origin {
            type ipi-sr-types:srte_protocol_origin_type_type_t;
        description
            "Instantiation mechanism used to create the candidate  path";
        }

        leaf originator {
            type  string;
        description
            "Identifier (concatenation of ASN and node-address) of
                    the node that signalled/instantiated the candidate
                    path on headend";
        }

        leaf name {
            type  string;
        description
            "User friendly name of the SR Policy";
        }

        leaf is-valid {
            type  boolean;
        description
            "Specifies the state of candidate path";
        }
    }

    notification sr-policy-binding-sid-unavailable-event {

        description "This notification is sent when same SR policy binding-sid configured for different SR-policy.";

        // severity "MAJOR";
        // eventClass "STATE";
        leaf name {
            type  string;
        description
            "User friendly name of the SR Policy";
        }

        leaf bsid-value {
            type  uint32;
        description
            "configurable value for static binding sid";
        }
    }

}

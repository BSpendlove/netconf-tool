/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-watchdog-types.yang
*
*/

module ipi-watchdog-types {

    yang-version 1.1;

    namespace   "http://www.ipinfusion.com/yang/ocnos/ipi-watchdog-types";

    prefix "ipi-watchdog-types";

    organization
        "IP Infusion Inc.";

    contact
        "Address: 3965 Freedom Circle, Suite 200, Santa Clara, CA 95054
         Phone: +1 408-400-1900
         E-mail: support@ipinfusion.com
         Web: http://www.ipinfusion.com/";

    description
        "Protocol modules watchdog datatypes";


    revision "2021-11-30" {
        description "Removed the type WATCHDOG_MODULE_STATUS_T. The new attribute is using CML_EMPTY_T";
        reference " 0.1.3.";
    }

    revision "2021-07-30" {
        description "PSERV restructured";
        reference "Initial Version";
    }



    typedef  watchdog_status_t {
        type enumeration {
            enum disabled {
                value 0;
                description "Watchdog status is disabled globally";
            }
            enum enabled {
                value 1;
                description "Watchdog status is enabled globally";
            }
        }
        description "type definition for WATCHDOG_STATUS_T";
    }

    typedef  watchdog_module_name_t {
        type enumeration {
            enum nsm {
                value 1;
                description "Software watchdog for NSM module";
            }
            enum ripd {
                value 2;
                description "Software watchdog for RIP module";
            }
            enum ripngd {
                value 3;
                description "Software watchdog for RIPNG module";
            }
            enum ospfd {
                value 4;
                description "Software watchdog for OSPF module";
            }
            enum ospf6d {
                value 5;
                description "Software watchdog for OSPF6 module";
            }
            enum isisd {
                value 6;
                description "Software watchdog for ISIS module";
            }
            enum hostpd {
                value 7;
                description "Software watchdog for HOSTP module";
            }
            enum ldpd {
                value 8;
                description "Software watchdog for LDP module";
            }
            enum rsvpd {
                value 9;
                description "Software watchdog for RSVP module";
            }
            enum mribd {
                value 10;
                description "Software watchdog for MRIB module";
            }
            enum pimd {
                value 11;
                description "Software watchdog for PIM module";
            }
            enum authd {
                value 13;
                description "Software watchdog for AUTH module";
            }
            enum mstpd {
                value 17;
                description "Software watchdog for MSTP module";
            }
            enum imi {
                value 18;
                description "Software watchdog for IMI module";
            }
            enum onmd {
                value 24;
                description "Software watchdog for ONM module";
            }
            enum hsl {
                value 26;
                description "Software watchdog for HSL module";
            }
            enum oamd {
                value 28;
                description "Software watchdog for OAM module";
            }
            enum vlogd {
                value 30;
                description "Software watchdog for VLOG module";
            }
            enum vrrpd {
                value 39;
                description "Software watchdog for VRRP module";
            }
            enum ndd {
                value 40;
                description "Software watchdog for NDD module";
            }
            enum ribd {
                value 42;
                description "Software watchdog for RIB module";
            }
            enum bgpd {
                value 44;
                description "Software watchdog for BGP module";
            }
            enum l2mribd {
                value 46;
                description "Software watchdog for L2MRIB module";
            }
            enum lagd {
                value 49;
                description "Software watchdog for LAG module";
            }
            enum sflow {
                value 50;
                description "Software watchdog for SFLOW module";
            }
            enum udld {
                value 51;
                description "Software watchdog for UDLD module";
            }
            enum cmld {
                value 52;
                description "Software watchdog for CML module";
            }
            enum cmmd {
                value 69;
                description "Software watchdog for CMM module";
            }
            enum pcepd {
                value 72;
                description "Software watchdog for PCEP module";
            }
        }
        description "type definition for WATCHDOG_MODULE_NAME_T";
    }

    typedef  watchdog_global_processes_status_t {
        type enumeration {
            enum not-running {
                value 0;
                description "At least one process is not running";
            }
            enum all-running {
                value 1;
                description "All processes are running";
            }
        }
        description "type definition for WATCHDOG_GLOBAL_PROCESSES_STATUS_T";
    }

    typedef  watchdog_process_status_t {
        type enumeration {
            enum not-running {
                value 0;
                description "Process not running";
            }
            enum running {
                value 1;
                description "Process running";
            }
        }
        description "type definition for WATCHDOG_PROCESS_STATUS_T";
    }

}

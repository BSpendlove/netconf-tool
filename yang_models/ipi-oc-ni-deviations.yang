module ipi-oc-ni-deviations {
  namespace   "http://www.ipinfusion.com/yang/ocnos/ipi-oc-ni-deviations";
  prefix "ipi-oc-ni-deviations";

  import openconfig-network-instance { prefix oc-netinst; }
  import openconfig-network-instance-types { prefix oc-ni-types; }
  import openconfig-bgp-types { prefix oc-bgp-types; }
  import openconfig-policy-types { prefix oc-pol-types; }

  revision "2022-02-04" {
    description "Added OSPFv2 area restriction to always be set with interface.";
  }

  revision "2022-01-19" {
    description "Removed unsupported protocols.";
  }

  revision "2021-09-13" {
    description "Protocol leaf identifier could not have space characters, leaf name could not have text for BGP, leaf local-as could not be set together with leaf peer-group, and peer-group-name have length limitation.";
  }

  revision "2020-01-27";

  deviation /oc-netinst:network-instances/oc-netinst:network-instance/oc-netinst:afts {
    deviate not-supported;
  }

  deviation /oc-netinst:network-instances/oc-netinst:network-instance/oc-netinst:evpn {
    deviate not-supported;
  }

  deviation /oc-netinst:network-instances/oc-netinst:network-instance/oc-netinst:mpls/oc-netinst:lsps {
    deviate not-supported;
  }

  deviation /oc-netinst:network-instances/oc-netinst:network-instance/oc-netinst:policy-forwarding {
    deviate not-supported;
  }

  deviation 	/oc-netinst:network-instances/oc-netinst:network-instance/oc-netinst:protocols/oc-netinst:protocol/oc-netinst:igmp {
    deviate not-supported;
  }

  deviation /oc-netinst:network-instances/oc-netinst:network-instance/oc-netinst:protocols/oc-netinst:protocol/oc-netinst:isis {
    deviate not-supported;
  }

  deviation 	/oc-netinst:network-instances/oc-netinst:network-instance/oc-netinst:protocols/oc-netinst:protocol/oc-netinst:local-aggregates {
    deviate not-supported;
  }

  deviation 	/oc-netinst:network-instances/oc-netinst:network-instance/oc-netinst:protocols/oc-netinst:protocol/oc-netinst:pim {
    deviate not-supported;
  }

  deviation /oc-netinst:network-instances/oc-netinst:network-instance/oc-netinst:segment-routing {
    deviate not-supported;
  }

  deviation  /oc-netinst:network-instances/oc-netinst:network-instance/oc-netinst:protocols/oc-netinst:protocol/oc-netinst:bgp/oc-netinst:peer-groups/oc-netinst:peer-group/oc-netinst:config/oc-netinst:peer-group-name {
    deviate replace {
      type string {
        length "1 .. 254";
      }
    }
  }

  deviation /oc-netinst:network-instances/oc-netinst:network-instance/oc-netinst:protocols/oc-netinst:protocol/oc-netinst:bgp/oc-netinst:neighbors/oc-netinst:neighbor/oc-netinst:config/oc-netinst:local-as {
    deviate add {
      must "not(../oc-netinst:peer-group)" {
        error-message "Cannot set local-as if peer-group is configured too";
      }
    }
  }

  deviation /oc-netinst:network-instances/oc-netinst:network-instance/oc-netinst:protocols/oc-netinst:protocol/oc-netinst:config/oc-netinst:name {
    deviate add {
      must "(../oc-netinst:identifier = 'oc-pol-types:BGP') and boolean(number(.))" {
        error-message "BGP instance name must be numeric";
      }
    }
  }

  deviation /oc-netinst:network-instances/oc-netinst:network-instance/oc-netinst:config/oc-netinst:type {
    deviate add {
      default 'oc-ni-types:L3VRF';
      must "(. != 'oc-ni-types:L2VSI') and (. != 'oc-ni-types:L2P2P')" {
        error-message "This instance type is not supported";
      }
    }
  }

  deviation /oc-netinst:network-instances/oc-netinst:network-instance/oc-netinst:config/oc-netinst:name {
    deviate add {
      must "(../oc-netinst:type != 'oc-ni-types:DEFAULT_INSTANCE') or (. = 'default')" {
        error-message "For DEFAULT instances the name must be 'default'";
      }

      must "(../oc-netinst:type != 'oc-ni-types:L2L3') or ((number(.) >= 1) and (number(.) <= 32))" {
        error-message "For L2L3 instances the name must be a number from 1 to 32";
      }
    }
  }

  deviation /oc-netinst:network-instances/oc-netinst:network-instance/oc-netinst:encapsulation/oc-netinst:config/oc-netinst:encapsulation-type {
    deviate add {
      must ". = 'oc-ni-types:MPLS' and ../oc-netinst:label-allocation-mode";
    }
  }

  deviation /oc-netinst:network-instances/oc-netinst:network-instance/oc-netinst:encapsulation/oc-netinst:config/oc-netinst:label-allocation-mode {
    deviate add {
      must ". != 'oc-ni-types:PER_NEXTHOP'";
    }
  }

  deviation /oc-netinst:network-instances/oc-netinst:network-instance/oc-netinst:table-connections/oc-netinst:table-connection/oc-netinst:config/oc-netinst:default-import-policy {
    deviate add {
      must "(. = 'ACCEPT_ROUTE')";
    }
  }

  deviation /oc-netinst:network-instances/oc-netinst:network-instance/oc-netinst:table-connections/oc-netinst:table-connection/oc-netinst:config/oc-netinst:import-policy {
    deviate add {
      max-elements 1;
    }
  }

  deviation /oc-netinst:network-instances/oc-netinst:network-instance/oc-netinst:config/oc-netinst:enabled {
    deviate add {
      must ". = 'true'";
    }
  }

  deviation /oc-netinst:network-instances/oc-netinst:network-instance/oc-netinst:config/oc-netinst:enabled-address-families {
    deviate replace {
      config false;
    }
  }

  deviation /oc-netinst:network-instances/oc-netinst:network-instance/oc-netinst:config/oc-netinst:mtu {
    deviate not-supported;
  }

  deviation /oc-netinst:network-instances/oc-netinst:network-instance/oc-netinst:mpls/oc-netinst:signaling-protocols/oc-netinst:ldp/oc-netinst:targeted/oc-netinst:address-families/oc-netinst:address-family/oc-netinst:targets/oc-netinst:target/oc-netinst:config/oc-netinst:enabled {
    deviate replace {
      config false;
    }
  }

  deviation /oc-netinst:network-instances/oc-netinst:network-instance/oc-netinst:protocols/oc-netinst:protocol/oc-netinst:bgp/oc-netinst:neighbors/oc-netinst:neighbor/oc-netinst:config/oc-netinst:peer-type {
    deviate not-supported;
  }

  deviation /oc-netinst:network-instances/oc-netinst:network-instance/oc-netinst:protocols/oc-netinst:protocol/oc-netinst:bgp/oc-netinst:neighbors/oc-netinst:neighbor/oc-netinst:config/oc-netinst:remove-private-as {
    deviate add {
        must "(. = 'oc-bgp-types:PRIVATE_AS_REMOVE_ALL')";
    }
  }

  deviation /oc-netinst:network-instances/oc-netinst:network-instance/oc-netinst:protocols/oc-netinst:protocol/oc-netinst:bgp/oc-netinst:neighbors/oc-netinst:neighbor/oc-netinst:apply-policy {
    deviate not-supported;
  }

  deviation /oc-netinst:network-instances/oc-netinst:network-instance/oc-netinst:interfaces/oc-netinst:interface/oc-netinst:config/oc-netinst:id {
    deviate replace {
      type string {
        length "1 .. 33";
      }
    }
  }

  deviation /oc-netinst:network-instances/oc-netinst:network-instance/oc-netinst:protocols/oc-netinst:protocol/oc-netinst:static-routes/oc-netinst:static {
    deviate add {
        must "((../../../../oc-netinst:config/oc-netinst:type != 'oc-ni-types:L3VRF') or " +
           "(oc-netinst:next-hops/oc-netinst:next-hop/oc-netinst:interface-ref/oc-netinst:config/oc-netinst:interface != ''))";
    }
  }

  deviation /oc-netinst:network-instances/oc-netinst:network-instance/oc-netinst:mpls/oc-netinst:signaling-protocols/oc-netinst:ldp/oc-netinst:targeted/oc-netinst:address-families/oc-netinst:address-family/oc-netinst:targets/oc-netinst:target/oc-netinst:config/oc-netinst:enabled {
    deviate add {
      must ". = 'true'";
    }
  }

  deviation /oc-netinst:network-instances/oc-netinst:network-instance/oc-netinst:protocols/oc-netinst:protocol/oc-netinst:static-routes/oc-netinst:static/oc-netinst:next-hops/oc-netinst:next-hop {
    deviate add {
        min-elements 1;
    }
  }

  deviation /oc-netinst:network-instances/oc-netinst:network-instance/oc-netinst:connection-points/oc-netinst:connection-point/oc-netinst:endpoints/oc-netinst:endpoint/oc-netinst:config/oc-netinst:endpoint-id {
    deviate add {
      must "((. = '1') or (. = '2'))";
    }
  }

  deviation /oc-netinst:network-instances/oc-netinst:network-instance/oc-netinst:connection-points/oc-netinst:connection-point/oc-netinst:endpoints/oc-netinst:endpoint/oc-netinst:config/oc-netinst:precedence {
    deviate add {
      must ". = ../oc-netinst:endpoint-id";
    }
  }

  deviation /oc-netinst:network-instances/oc-netinst:network-instance/oc-netinst:connection-points/oc-netinst:connection-point/oc-netinst:config/oc-netinst:connection-point-id {
    deviate add {
      must ". = 'default'";
    }
  }

  deviation /oc-netinst:network-instances/oc-netinst:network-instance/oc-netinst:route-limits {
    deviate not-supported;
  }

  deviation /oc-netinst:network-instances/oc-netinst:network-instance/oc-netinst:protocols/oc-netinst:protocol/oc-netinst:ospfv2/oc-netinst:areas/oc-netinst:area {
    deviate add {
      must "/oc-netinst:network-instances/oc-netinst:network-instance/oc-netinst:protocols/oc-netinst:protocol/oc-netinst:ospfv2/oc-netinst:areas/oc-netinst:area/oc-netinst:interfaces/oc-netinst:interface" {
        error-message "Area cannot be set without interface";
      }
    }
  }
}

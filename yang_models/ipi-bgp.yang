/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-bgp.yang
*
*/

module ipi-bgp {

    yang-version 1.1;

    namespace   "http://www.ipinfusion.com/yang/ocnos/ipi-bgp";

    prefix "ipi-bgp";

    import cml-data-types {
        prefix cml-data-types;
        revision-date 2022-04-04;
    }

    import ipi-bgp-types {
        prefix ipi-bgp-types;
        revision-date 2022-01-17;
    }

    import ipi-network-instance {
        prefix ipi-network-instance;
        revision-date 2021-11-10;
    }

    import ipi-vrf {
        prefix ipi-vrf;
        revision-date 2021-09-03;
    }

    import feature-list {
        prefix feature-list;
        revision-date 2022-07-13;
    }

    include ipi-bgp-instance { revision-date 2022-01-17;}
    include ipi-bgp-common { revision-date 2022-01-17;}
    include ipi-bgp-address-family { revision-date 2022-01-17;}
    include ipi-bgp-evpn-rib { revision-date 2021-09-03;}
    include ipi-bgp-peer-group { revision-date 2022-01-07;}
    include ipi-bgp-peer { revision-date 2022-01-17;}
    include ipi-bgp-address-family-vrf { revision-date 2022-01-17;}
    include ipi-bgp-link-state { revision-date 2021-10-03;}
    include ipi-bgp-epe { revision-date 2022-02-28;}
    organization
        "IP Infusion Inc.";

    contact
        "Address: 3965 Freedom Circle, Suite 200, Santa Clara, CA 95054
         Phone: +1 408-400-1900
         E-mail: support@ipinfusion.com
         Web: http://www.ipinfusion.com/";

    description
        "YANG version of the ipi-bgp";


    revision "2022-02-28" {
        description "Modified EPE Backup attributes heirarchy";
        reference " 0.8.17.";
    }

    revision "2022-01-17" {
        description "Modified Submodule";
        reference " 0.8.16.";
    }

    revision "2022-01-11" {
        description "Modified Submodule";
        reference " 0.8.15.";
    }

    revision "2022-01-10" {
        description "Added depenedency constraint between 'vrf address-family and route-redistribu
tion' and rd_string/IP-VRF";
        reference " 0.8.14.";
    }

    revision "2021-11-17" {
        description "SKU compilation error fixes";
        reference " 0.8.13.";
    }

    revision "2021-10-03" {
        description "Added new BGP-LS-EPE runtime attributes";
        reference " 0.8.12.";
    }

    revision "2021-09-20" {
        description "Spelling has been corrected for an attribute";
        reference " 0.8.11.";
    }

    revision "2021-09-15" {
        description "deprecated the bgp additional-paths CLI under bgp mode and removed the yang drop element for the additional-path attriute for the bgp-add-path feature";
        reference " 0.8.10.";
    }

    revision "2021-09-03" {
        description "Update descriptions of attribute";
        reference " 0.8.9.";
    }

    revision "2021-08-26" {
        description "Added dependency constraint between auth-key-encrypt and password attrs for the peer authentication password CLI";
        reference " 0.8.8.";
    }

    revision "2021-08-25" {
        description "Dependent object addition for bgp-vrf configs";
        reference " 0.8.7.";
    }

    revision "2021-08-19" {
        description "MPLS nexthop tracking command is added";
        reference " 0.8.6.";
    }

    revision "2021-08-16" {
        description "Removed the Yang drop element and updated the datatype from enum to bits for the additional-paths-mode attribute";
        reference " 0.8.5.";
    }

    revision "2021-08-13" {
        description "BGP ECMP Support for EIBGP routes";
        reference " 0.8.4.";
    }

    revision "2021-08-09" {
        description "Added support for BGP-EPE feature";
        reference " 0.8.2.";
    }

    revision "2021-08-03" {
        description "Added new attribute for enabling Enhe capability for IPv6 VPNv4 peer";
        reference " 0.8.3.";
    }

    revision "2021-07-27" {
        description "Added support for BGP-LS operational attributes";
        reference " 0.8.1.";
    }

    revision "2021-07-21" {
        description "Added bgp evpn get api attributes in dependent data models";
        reference " 0.8.0.";
    }

    revision "2021-07-05" {
        description "Remodelled authentication password object list for BGP peer, VRF peer and peer-group";
        reference " 0.7.0.";
    }

    revision "2021-06-25" {
        description "Modified dependency for neighbor activate attribute";
        reference " 0.6.9.";
    }

    revision "2021-06-21" {
        description "Corrected the CLI for the RPC bgp-debug-updates-type-on";
        reference " 0.6.8.";
    }

    revision "2021-06-11" {
        description "Added dependency constraint between name and direction attrs for the distribute-list, prefix-list, filter-list and route-map CLI's Added dependency constraint for graceful-restart CLI's restart-time, stale-path-max-retention-time and graceful-reset";
        reference " 0.6.7.";
    }

    revision "2021-06-09" {
        description "Removal of default ipv4 unicast activate and fix for DB sync issues";
        reference " 0.6.6.";
    }

    revision "2021-06-07" {
        description "Deprecated 'connect-retry-interval', duplicate of 'peer-connect-interval'";
        reference " 0.6.5.";
    }

    revision "2021-05-31" {
        description "Deprecated prefix-list-count attribute and added length for route map name";
        reference " 0.6.4.";
    }

    revision "2021-05-28" {
        description "Changed type of the attribute default-originate-information-sent";
        reference " 0.6.3.";
    }

    revision "2021-05-26" {
        description "Deprecated the as-local-count run-time attribute is same as the configured local-as attribute";
        reference " 0.6.2.";
    }

    revision "2021-05-13" {
        description "Removed dependency validation on AF activate for allow-ebgp-vpn attribute";
        reference " 0.6.1.";
    }

    revision "2021-05-05" {
        description "Added change for bgp unnumbered feature ";
        reference " 0.6.0.";
    }

    revision "2021-04-27" {
        description "Added leafref for vrf-name in mpls-l3vpn-label-mode ";
        reference " 0.6.0.";
    }

    revision "2021-04-09" {
        description "Change related to Peer group remodelling";
        reference " 0.5.0.";
    }

    revision "2021-03-31" {
        description "Added support for configuring BFD for BGP peer under VRF address family";
        reference " 0.4.0.";
    }

    revision "2021-03-05" {
        description "Community-list related changes";
        reference " 0.3.0.";
    }

    revision "2020-12-15" {
        description "Change to have data-types in lower case instead of camel case";
        reference " 0.2.0.";
    }

    revision "2020-09-10" {
        description "Initial Version";
        reference " 0.1.0.";
    }

    grouping bgp-global-common-config {
        description
            "global common configuration in BGP";
        leaf enable-aggregate-nexthop  {
            type  empty;
            description "Use this attribute to set the BGP option to perform aggregation only
                        when next-hop matches the specified IP address.";
        } // END of enable-aggregate-nexthop definition.

        leaf enable-path-select  {
            type  empty;
            description "Use this attribute to set RFC 1771 compatible path selection";
        } // END of enable-path-select definition.

        leaf disable-adj-out  {
            type  empty;
            description "Use this attribute to Disable BGP ADJ_OUT.";
        } // END of disable-adj-out definition.

        leaf enable-extended-asn-capability  {
            if-feature feature-list:HAVE_EXT_CAP_ASN;
            type  empty;
            description "Use this attribute to configure a BGP router to send 4-octet ASN
                        capabilities. If attempting to change the AS capability from 2 to 4 or
                        4 to 2, a prompt occurs to remove the VRF configuration (if it
                        exists), and reconfiguration is required,because the route
                        distinguisher (RD) configuration would have been created with the
                        current (2 octet or 4 octet) capability, and must be reconfigured
                        before attempting to change the capability. While loading from a saved
                        configuration with AS4 capability and BGP VRF configuration, the
                        capability will not be changed because of the above described reason.";
        } // END of enable-extended-asn-capability definition.

        leaf enable-nexthop-tracking  {
            type  empty;
            description "Use this attribute to enable nexthop address tracking. Nexthop address
                        tracking is an event-driven notification system that monitors the
                        status of routes installed in the Routing Information Base (RIB) and
                        reports nexthop changes that affect internal BGP (iBGP) or external
                        BGP (eBGP) prefixes directly to the BGP process. This improves the
                        overall BGP convergence time, by allowing BGP to respond rapidly to
                        nexthop changes for routes installed in the RIB. If nexthop tracking
                        is enabled after certain routes are learned, the registration of all
                        nexthops for selected BGP routes is done after the nexthop tracking
                        feature is enabled. If nexthop tracking is disabled, and if there are
                        still some selected BGP routes, BGP de-registers the nexthops of all
                        selected BGP routes from NSM.";
        } // END of enable-nexthop-tracking definition.

        leaf nexthop-tracking-delay  {
            when " /ipi-bgp:bgp/ipi-bgp:global/ipi-bgp:config/ipi-bgp:enable-nexthop-tracking ";
            type  uint8 {
                 range "1..100"  {
                    description "1..100:Nexthop Trigger Delay time interval between 1 and 100";
                 }
            }
            default "5";
            description "Use this attribute to set the delay time for nexthop address tracking.
                        This attribute configures the delayinterval between routing table
                        walks for nexthop delay tracking, after which BGP does a routing table
                        scan on receiving a nexthop change trigger from NSM. The time period
                        determines how long BGP waits before it walks the full BGP table to
                        determine which prefixes are affected by the nexthop changes, after it
                        receives the trigger from NSM about one or more nexthop changes.";
        } // END of nexthop-tracking-delay definition.

        leaf enable-rfc-1771-strict-origin  {
            type  empty;
            description "Use this attribute to set the origin path attribute to IGP when the
                        origin is a protocol such as RIP, OSPF,or ISIS as specified in RFC
                        1771. Otherwise, the origin is always set to incomplete which is the
                        industry standard.";
        } // END of enable-rfc-1771-strict-origin definition.

        leaf config-type  {
            type  ipi-bgp-types:bgp_config_t;
            description "Use this attribute to set the BGP configuration to the standard type.
                        After setting the configuration to the standard type, use th
                        sendCommunity attribute to send out BGP community attributes. The
                        zebos configuration type is the default and requires no specific
                        configuration for sending out BGP standard community and extended
                        community attributes.";
        } // END of config-type definition.

    } // END of bgp-global-common-config definition.
    grouping bgp-global-common {
        description
            "global common configuration in BGP";
        container config {
            description
                "Configuration parameters relating to the BGP global";
            uses bgp-global-common-config;
        } // END of config-container definition.
        container state {
            config false;
            description
                "state parameters relating to the BGP global";
            uses bgp-global-common-config;
        } // END of state-container definition.
    } // END of bgp-global-common definition.
    grouping bgp-mpls-l3vpn-config {
        description
            "bgp mpls l3 vpn configuration";
        leaf address-family-name  {
            type  ipi-bgp-types:bgp_af_config_t;
            description "Use this attribute to specify address family name";
        } // END of address-family-name definition.

        leaf vrf-name  {
            type  leafref {
                path  "/ipi-network-instance:network-instances/ipi-network-instance:network-instance/ipi-vrf:vrf/ipi-vrf:config/ipi-vrf:vrf-name";
            }
            description "Use this attribute to specify vrf name";
        } // END of vrf-name definition.

        leaf label-alloc-type  {
            type  ipi-bgp-types:bgp_l3vpn_label_alloc_mode_t;
            mandatory true;
            description "Use this attribute to specify label alloc type";
        } // END of label-alloc-type definition.

    } // END of bgp-mpls-l3vpn-config definition.
    grouping bgp-mpls-l3-vpn {
        description
            "bgp mpls l3 vpn cnfiguration";

        list mpls-l3vpn-label-mode {
            if-feature feature-list:HAVE_MPLS;
            key "address-family-name vrf-name";
            description
                "bgp mpls l3 vpn cnfiguration";
            leaf address-family-name  {
                type  leafref {
                    path  "../config/address-family-name";
                }
                description "Use this attribute to specify address family name";
            } // END of address-family-name definition.

            leaf vrf-name  {
                type  leafref {
                    path  "../config/vrf-name";
                }
                description "Use this attribute to specify vrf name";
            } // END of vrf-name definition.

            container config {
                description
                    "configuration parameters relating to bgp mpls l3 vpn";
                uses bgp-mpls-l3vpn-config;
            } // END of config-container definition.
            container state {
                config false;
                description
                    "state parameters relating to bgp mpls l3 vpn";
                uses bgp-mpls-l3vpn-config;
            } // END of state-container definition.
        } // End of mpls-l3vpn-label-mode-list
    } // END of bgp-mpls-l3-vpn definition.
    grouping bgp-community-list-action-value-config {
        description
            "bgp community list action config";
        leaf action  {
            type  ipi-bgp-types:bgp_community_list_action_t;
            description "community type";
        } // END of action definition.

        leaf value  {
            type  string {
                length "1..1965";
                pattern "[^?'=,>|]*";
            }
            description "Use the community-list to specify BGP community attributes. The
                        community attribute is used for implementing policy routing. It is an
                        optional, transitive attribute and facilitates transfer of local
                        policies through different autonomous systems.";
        } // END of value definition.

    } // END of bgp-community-list-action-value-config definition.
    grouping bgp-community-list-standard-number-action-any-config {
        description
            "grouping for bgp community list standard action";
        leaf action-name  {
            type  ipi-bgp-types:bgp_community_list_action_t;
            mandatory true;
            description "Use this attribute to specify a standard community list (1 to 99) that
                        specifies BGP community attributes.";
        } // END of action-name definition.

    } // END of bgp-community-list-standard-number-action-any-config definition.
    grouping bgp-community-list-standard-number-action-any {
        description
            "bgp community list standard action for any";
        container action-for-any {
            description
                "container for community-list action for any";
            container config {
                presence "To configure action for any standard community";
                description
                    "configuration parameters relating to action for any standard community";
                uses bgp-community-list-standard-number-action-any-config;
            } // END of config-container definition.
            container state {
                config false;
                description
                    "state parameters relating to standard action";
                uses bgp-community-list-standard-number-action-any-config;
            } // END of state-container definition.
        } // END of action-for-any-container definition.
    } // END of bgp-community-list-standard-number-action-any definition.
    grouping bgp-community-list-standard-number-action-value-config {
        description
            "bgp community list standard action list value";
        leaf action-standard-number  {
            type  ipi-bgp-types:bgp_community_list_action_t;
            description "Use this attribute to specify a standard community list (1 to 99) that
                        specifies BGP community attributes.";
        } // END of action-standard-number definition.

        leaf standard-number-value  {
            type  string {
                length "1..1965";
                pattern "[^?'=,>|]*";
            }
            description "Use this attribute to specify a standard community list (1 to 99) that
                        specifies BGP community attributes.";
        } // END of standard-number-value definition.

    } // END of bgp-community-list-standard-number-action-value-config definition.
    grouping bgp-community-list-standard-number-action-value {
        description
            "bgp community list standard action list value";

        list action-list-value {
            key "action-standard-number standard-number-value";
            description
                "bgp action list value";
            leaf action-standard-number  {
                type  leafref {
                    path  "../config/action-standard-number";
                }
                description "Use this attribute to specify a standard community list (1 to 99) that
                            specifies BGP community attributes.";
            } // END of action-standard-number definition.

            leaf standard-number-value  {
                type  leafref {
                    path  "../config/standard-number-value";
                }
                description "Use this attribute to specify a standard community list (1 to 99) that
                            specifies BGP community attributes.";
            } // END of standard-number-value definition.

            container config {
                description
                    "configuration parameters relating to  bgp action list value";
                uses bgp-community-list-standard-number-action-value-config;
            } // END of config-container definition.
            container state {
                config false;
                description
                    "state parameters relating to  bgp action list value";
                uses bgp-community-list-standard-number-action-value-config;
            } // END of state-container definition.
        } // End of action-list-value-list
    } // END of bgp-community-list-standard-number-action-value definition.
    grouping bgp-community-list-number-config {
        description
            "bgp community list number configuration";
        leaf standard-number  {
            type  uint32 {
                 range "1..99"  {
                    description "1..99:Community list number (standard)";
                 }
            }
            description "Community list standard number";
        } // END of standard-number definition.

    } // END of bgp-community-list-number-config definition.
    grouping bgp-community-list-number {
        description
            "bgp community list number configuration";

        list numbered {
        when " /ipi-bgp:bgp/ipi-bgp:global/ipi-bgp:community-lists/ipi-bgp:numbered/ipi-bgp:action-list-value/ipi-bgp:action-standard-number  or /ipi-bgp:bgp/ipi-bgp:global/ipi-bgp:community-lists/ipi-bgp:numbered/ipi-bgp:action-list-value/ipi-bgp:standard-number-value  or /ipi-bgp:bgp/ipi-bgp:global/ipi-bgp:community-lists/ipi-bgp:numbered/ipi-bgp:action-for-any/ipi-bgp:config/ipi-bgp:action-name ";
            key "standard-number";
            description
                "bgp community list number";
            leaf standard-number  {
                type  leafref {
                    path  "../config/standard-number";
                }
                description "Community list standard number";
            } // END of standard-number definition.

            container config {
                description
                    "configuration parameters relating to bgp community list number";
                uses bgp-community-list-number-config;
            } // END of config-container definition.
            container state {
                config false;
                description
                    "state parameters relating to bgp community list number";
                uses bgp-community-list-number-config;
            } // END of state-container definition.
            uses bgp-community-list-standard-number-action-any;
            uses bgp-community-list-standard-number-action-value;
        } // End of numbered-list
    } // END of bgp-community-list-number definition.
    grouping bgp-community-list-action-value-standard-config {
        description
            "bgp community list action standard list config";
        leaf action-name-standard  {
            type  ipi-bgp-types:bgp_community_list_action_t;
            description "Use the community-lists to specify BGP community attributes. The
                        community attribute is used for implementing policy routing. It is an
                        optional, transitive attribute and facilitates transfer of local
                        policies through different autonomous systems. It includes community
                        values that are 32 bits long. There are two kinds of community-lists:
                        expanded and standard. The standard community-list defines the
                        community attributes in a specified format without regular
                        expressions. The expanded community-list defines the community
                        attributes with regular expressions.Use this attribute to add a
                        standard community-list entry. The standard community-list is compiled
                        into binary format and is directly compared with the BGP communities
                        attribute in the BGP updates. The comparison is faster than the
                        expanded community-list. Any community value that does not match the
                        standard community value is automatically treated as expanded.";
        } // END of action-name-standard definition.

        leaf community-value-standard  {
            type  string {
                length "1..1965";
                pattern "[^?' =,>|]+";
            }
            description "Use this attribute to specify standard community";
        } // END of community-value-standard definition.

    } // END of bgp-community-list-action-value-standard-config definition.
    grouping bgp-community-list-action-value-standard {
        description
            "bgp community list action standard list config";

        list action-value {
            key "action-name-standard community-value-standard";
            description
                "community list action";
            leaf action-name-standard  {
                type  leafref {
                    path  "../config/action-name-standard";
                }
                description "Use the community-lists to specify BGP community attributes. The
                            community attribute is used for implementing policy routing. It is an
                            optional, transitive attribute and facilitates transfer of local
                            policies through different autonomous systems. It includes community
                            values that are 32 bits long. There are two kinds of community-lists:
                            expanded and standard. The standard community-list defines the
                            community attributes in a specified format without regular
                            expressions. The expanded community-list defines the community
                            attributes with regular expressions.Use this attribute to add a
                            standard community-list entry. The standard community-list is compiled
                            into binary format and is directly compared with the BGP communities
                            attribute in the BGP updates. The comparison is faster than the
                            expanded community-list. Any community value that does not match the
                            standard community value is automatically treated as expanded.";
            } // END of action-name-standard definition.

            leaf community-value-standard  {
                type  leafref {
                    path  "../config/community-value-standard";
                }
                description "Use this attribute to specify standard community";
            } // END of community-value-standard definition.

            container config {
                description
                    "configuration parameters relating to bgp community-list-action";
                uses bgp-community-list-action-value-standard-config;
            } // END of config-container definition.
            container state {
                config false;
                description
                    "state parameters relating to bgp community-list-action";
                uses bgp-community-list-action-value-standard-config;
            } // END of state-container definition.
        } // End of action-value-list
    } // END of bgp-community-list-action-value-standard definition.
    grouping bgp-community-list-action-for-any-standard-config {
        description
            "grouping for bgp community list standard action";
        leaf action-name  {
            type  ipi-bgp-types:bgp_community_list_action_t;
            mandatory true;
            description "Use this attribute to specify a standard community list (1 to 99) that
                        specifies BGP community attributes.";
        } // END of action-name definition.

    } // END of bgp-community-list-action-for-any-standard-config definition.
    grouping bgp-community-list-action-for-any-standard {
        description
            "bgp community list standard action for any";
        container action-for-any {
            description
                "container for community-list action for any";
            container config {
                presence "To configure action for any standard community";
                description
                    "configuration parameters relating to action for any standard community";
                uses bgp-community-list-action-for-any-standard-config;
            } // END of config-container definition.
            container state {
                config false;
                description
                    "state parameters relating to standard action";
                uses bgp-community-list-action-for-any-standard-config;
            } // END of state-container definition.
        } // END of action-for-any-container definition.
    } // END of bgp-community-list-action-for-any-standard definition.
    grouping bgp-community-list-standard-config {
        description
            "bgp commmunity list standard configuration";
        leaf list-type  {
            type  ipi-bgp-types:bgp_community_list_type_t;
            description "Community list standard type";
        } // END of list-type definition.

        leaf name  {
            type  string {
                length "1..1965";
                pattern "[^?' =,>|]+";
            }
            description "Community list standard name";
        } // END of name definition.

    } // END of bgp-community-list-standard-config definition.
    grouping bgp-community-list-standard {
        description
            "bgp commmunity list standard configuration";

        list standard {
        when " /ipi-bgp:bgp/ipi-bgp:global/ipi-bgp:community-lists/ipi-bgp:standard/ipi-bgp:action-value/ipi-bgp:action-name-standard  or /ipi-bgp:bgp/ipi-bgp:global/ipi-bgp:community-lists/ipi-bgp:standard/ipi-bgp:action-value/ipi-bgp:community-value-standard  or /ipi-bgp:bgp/ipi-bgp:global/ipi-bgp:community-lists/ipi-bgp:standard/ipi-bgp:action-for-any/ipi-bgp:config/ipi-bgp:action-name ";
            key "list-type name";
            description
                "bgp community list standard";
            leaf list-type  {
                type  leafref {
                    path  "../config/list-type";
                }
                description "Use this attribute to specify community list type";
            } // END of list-type definition.

            leaf name  {
                type  leafref {
                    path  "../config/name";
                }
                description "Use this attribute to specify community list name";
            } // END of name definition.

            container config {
                description
                    "configuration parameters relating to bgp community list standard";
                uses bgp-community-list-standard-config;
            } // END of config-container definition.
            container state {
                config false;
                description
                    "state parameters relating to bgp community list standard";
                uses bgp-community-list-standard-config;
            } // END of state-container definition.
            uses bgp-community-list-action-for-any-standard;
            uses bgp-community-list-action-value-standard;
        } // End of standard-list
    } // END of bgp-community-list-standard definition.
    grouping bgp-community-list-expanded-action-value-config {
        description
            "bgp community list expanded list action";
        leaf action-expanded  {
            type  ipi-bgp-types:bgp_community_list_action_t;
            description "Community list extended type";
        } // END of action-expanded definition.

        leaf regular-expression-list  {
            type  cml-data-types:cml_line_t {
                length "1..1965";
            }
            description "Use this attribute to specify ordered list as a regular-expression.";
        } // END of regular-expression-list definition.

    } // END of bgp-community-list-expanded-action-value-config definition.
    grouping bgp-community-list-expanded-action-value {
        description
            "bgp community list expanded list action";

        list action-value {
            key "action-expanded regular-expression-list";
            description
                "bgp community list expanded list action";
            leaf action-expanded  {
                type  leafref {
                    path  "../config/action-expanded";
                }
                description "Community list extended type";
            } // END of action-expanded definition.

            leaf regular-expression-list  {
                type  leafref {
                    path  "../config/regular-expression-list";
                }
                description "Use this attribute to specify ordered list as a regular-expression.";
            } // END of regular-expression-list definition.

            container config {
                description
                    "configuration parameters relating to bgp community list expanded list
                            action";
                uses bgp-community-list-expanded-action-value-config;
            } // END of config-container definition.
            container state {
                config false;
                description
                    "state parameters relating to bgp community list expanded list action";
                uses bgp-community-list-expanded-action-value-config;
            } // END of state-container definition.
        } // End of action-value-list
    } // END of bgp-community-list-expanded-action-value definition.
    grouping bgp-community-list-expanded-config {
        description
            "bgp community list expanded";
        leaf list-type  {
            type  ipi-bgp-types:bgp_expanded_list_t;
            description "Community list extended value";
        } // END of list-type definition.

        leaf expanded-type  {
            type  ipi-bgp-types:bgp_expanded_list_type_t;
            description "Community list extended value";
        } // END of expanded-type definition.

    } // END of bgp-community-list-expanded-config definition.
    grouping bgp-community-list-expanded {
        description
            "bgp community list expanded";

        list expanded-list {
        when " /ipi-bgp:bgp/ipi-bgp:global/ipi-bgp:community-lists/ipi-bgp:expanded-list/ipi-bgp:action-value/ipi-bgp:action-expanded  or /ipi-bgp:bgp/ipi-bgp:global/ipi-bgp:community-lists/ipi-bgp:expanded-list/ipi-bgp:action-value/ipi-bgp:regular-expression-list ";
            key "list-type expanded-type";
            description
                "bgp community list expanded";
            leaf list-type  {
                type  leafref {
                    path  "../config/list-type";
                }
                description "Community list expanded type";
            } // END of list-type definition.

            leaf expanded-type  {
                type  leafref {
                    path  "../config/expanded-type";
                }
                description "Community list extended value";
            } // END of expanded-type definition.

            container config {
                description
                    "configuration parameters relating to bgp community list expanded";
                uses bgp-community-list-expanded-config;
            } // END of config-container definition.
            container state {
                config false;
                description
                    "state parameters relating to bgp community list expanded";
                uses bgp-community-list-expanded-config;
            } // END of state-container definition.
            uses bgp-community-list-expanded-action-value;
        } // End of expanded-list-list
    } // END of bgp-community-list-expanded definition.
    grouping bgp-extended-number-community-list-action-value-config {
        description
            "bgp extended community list action config";
        leaf extended-action-number  {
            type  ipi-bgp-types:bgp_community_list_action_t;
            description "Extended Community list type";
        } // END of extended-action-number definition.

        leaf extended-value  {
            type  cml-data-types:cml_line_t {
                length "1..1965";
            }
            description "Use this attribute to create an entry for a standard extended
                        community list (1 to 99) that specifies BGP community attributes.";
        } // END of extended-value definition.

    } // END of bgp-extended-number-community-list-action-value-config definition.
    grouping bgp-extended-number-community-list-action-value {
        description
            "bgp extended community list action config";

        list action-value {
            key "extended-action-number extended-value";
            description
                "bgp extended community list action config";
            leaf extended-action-number  {
                type  leafref {
                    path  "../config/extended-action-number";
                }
                description "Extended Community list type";
            } // END of extended-action-number definition.

            leaf extended-value  {
                type  leafref {
                    path  "../config/extended-value";
                }
                description "Use this attribute to create an entry for a standard extended
                            community list (1 to 99) that specifies BGP community attributes.";
            } // END of extended-value definition.

            container config {
                description
                    "configuration parameters relating to bgp extended community list
                            action";
                uses bgp-extended-number-community-list-action-value-config;
            } // END of config-container definition.
            container state {
                config false;
                description
                    "state parameters relating to bgp extended community list action";
                uses bgp-extended-number-community-list-action-value-config;
            } // END of state-container definition.
        } // End of action-value-list
    } // END of bgp-extended-number-community-list-action-value definition.
    grouping bgp-extended-community-list-number-config {
        description
            "bgp extended community list number config";
        leaf standard-number  {
            type  uint32 {
                 range "1..99"  {
                    description "1..99:Extended Community list number (standard)";
                 }
            }
            description "Extended Community list number";
        } // END of standard-number definition.

    } // END of bgp-extended-community-list-number-config definition.
    grouping bgp-extended-community-list-number {
        description
            "bgp extended community list number config";

        list numbered {
        when " /ipi-bgp:bgp/ipi-bgp:global/ipi-bgp:community-lists/ipi-bgp:extended-community/ipi-bgp:numbered/ipi-bgp:action-value/ipi-bgp:extended-action-number  or /ipi-bgp:bgp/ipi-bgp:global/ipi-bgp:community-lists/ipi-bgp:extended-community/ipi-bgp:numbered/ipi-bgp:action-value/ipi-bgp:extended-value ";
            key "standard-number";
            description
                "bgp extended community list number config";
            leaf standard-number  {
                type  leafref {
                    path  "../config/standard-number";
                }
                description "Extended Community list number";
            } // END of standard-number definition.

            container config {
                description
                    "configuration parameters relating to bgp extended community list
                            number";
                uses bgp-extended-community-list-number-config;
            } // END of config-container definition.
            container state {
                config false;
                description
                    "state parameters relating to bgp extended community list number";
                uses bgp-extended-community-list-number-config;
            } // END of state-container definition.
            uses bgp-extended-number-community-list-action-value;
        } // End of numbered-list
    } // END of bgp-extended-community-list-number definition.
    grouping bgp-extended-community-standard-action-value-config {
        description
            "bgp extended community standard action config";
        leaf extended-action  {
            type  ipi-bgp-types:bgp_community_list_action_t;
            description "extcommunity Community list type";
        } // END of extended-action definition.

        leaf route-target-soo  {
            type  ipi-bgp-types:bgp_route_target_t;
            description "route-target soo";
        } // END of route-target-soo definition.

        leaf value  {
            type  string {
                length "1..1965";
                pattern "[^?' =,>|]+";
            }
            description "Use this attribute to create an entry for a standard extended
                        community list for rt (Route target extended community) or soo
                        (Site-of-origin extended community).";
        } // END of value definition.

    } // END of bgp-extended-community-standard-action-value-config definition.
    grouping bgp-extended-community-standard-action-value {
        description
            "bgp extended community standard action config";

        list action-value {
            key "extended-action route-target-soo value";
            description
                "bgp extended community standard action config";
            leaf extended-action  {
                type  leafref {
                    path  "../config/extended-action";
                }
                description "extcommunity Community list type";
            } // END of extended-action definition.

            leaf route-target-soo  {
                type  leafref {
                    path  "../config/route-target-soo";
                }
                description "route-target soo";
            } // END of route-target-soo definition.

            leaf value  {
                type  leafref {
                    path  "../config/value";
                }
                description "Use this attribute to create an entry for a standard extended
                            community list for rt (Route target extended community) or soo
                            (Site-of-origin extended community).";
            } // END of value definition.

            container config {
                description
                    "configuration parameters relating to bgp extended community standard
                            action";
                uses bgp-extended-community-standard-action-value-config;
            } // END of config-container definition.
            container state {
                config false;
                description
                    "state parameters relating to bgp extended community standard action";
                uses bgp-extended-community-standard-action-value-config;
            } // END of state-container definition.
        } // End of action-value-list
    } // END of bgp-extended-community-standard-action-value definition.
    grouping bgp-extended-community-standard-config {
        description
            "bgp extended community standard config";
        leaf name  {
            type  string {
                length "1..1965";
                pattern "[^?' =,>|]+";
            }
            description "extcommunity Community list name";
        } // END of name definition.

    } // END of bgp-extended-community-standard-config definition.
    grouping bgp-extended-community-standard {
        description
            "bgp extended community standard config";

        list standard {
        when " /ipi-bgp:bgp/ipi-bgp:global/ipi-bgp:community-lists/ipi-bgp:extended-community/ipi-bgp:standard/ipi-bgp:action-value/ipi-bgp:extended-action  or /ipi-bgp:bgp/ipi-bgp:global/ipi-bgp:community-lists/ipi-bgp:extended-community/ipi-bgp:standard/ipi-bgp:action-value/ipi-bgp:route-target-soo  or /ipi-bgp:bgp/ipi-bgp:global/ipi-bgp:community-lists/ipi-bgp:extended-community/ipi-bgp:standard/ipi-bgp:action-value/ipi-bgp:value ";
            key "name";
            description
                "bgp extended community standard config";
            leaf name  {
                type  leafref {
                    path  "../config/name";
                }
                description "Use this attribute to specify community list name";
            } // END of name definition.

            container config {
                description
                    "configuration parametrs relating to bgp extended community list
                            standard";
                uses bgp-extended-community-standard-config;
            } // END of config-container definition.
            container state {
                config false;
                description
                    "state parametrs relating to bgp extended community list standard";
                uses bgp-extended-community-standard-config;
            } // END of state-container definition.
            uses bgp-extended-community-standard-action-value;
        } // End of standard-list
    } // END of bgp-extended-community-standard definition.
    grouping bgp-extended-community-expanded-action-value-config {
        description
            "bgp extended community expanded action configurations";
        leaf action  {
            type  ipi-bgp-types:bgp_community_list_action_t;
            description "extcommunity Extended Community type";
        } // END of action definition.

        leaf value  {
            type  cml-data-types:cml_line_t {
                length "1..1965";
            }
            description "Use this attribute to create an extended community list";
        } // END of value definition.

    } // END of bgp-extended-community-expanded-action-value-config definition.
    grouping bgp-extended-community-expanded-action-value {
        description
            "bgp extended community expanded action configurations";

        list action-value {
            key "action value";
            description
                "bgp extended community expanded action configurations";
            leaf action  {
                type  leafref {
                    path  "../config/action";
                }
                description "extcommunity Extended Community type";
            } // END of action definition.

            leaf value  {
                type  leafref {
                    path  "../config/value";
                }
                description "Use this attribute to create an extended community list";
            } // END of value definition.

            container config {
                description
                    "configuration parameters relating to  bgp extended community expanded
                            action list";
                uses bgp-extended-community-expanded-action-value-config;
            } // END of config-container definition.
            container state {
                config false;
                description
                    "state parameters relating to  bgp extended community expanded action
                            list";
                uses bgp-extended-community-expanded-action-value-config;
            } // END of state-container definition.
        } // End of action-value-list
    } // END of bgp-extended-community-expanded-action-value definition.
    grouping bgp-extended-community-expanded-config {
        description
            "bgp extended community expanded configurations";
        leaf list-type  {
            type  ipi-bgp-types:bgp_expanded_list_t;
            description "Community list extended value";
        } // END of list-type definition.

        leaf expanded-type  {
            type  ipi-bgp-types:bgp_expanded_list_type_t;
            description "Community list extended value";
        } // END of expanded-type definition.

    } // END of bgp-extended-community-expanded-config definition.
    grouping bgp-extended-community-expanded {
        description
            "bgp extended community expanded configurations";

        list expanded-list {
        when " /ipi-bgp:bgp/ipi-bgp:global/ipi-bgp:community-lists/ipi-bgp:extended-community/ipi-bgp:expanded-list/ipi-bgp:action-value/ipi-bgp:action  or /ipi-bgp:bgp/ipi-bgp:global/ipi-bgp:community-lists/ipi-bgp:extended-community/ipi-bgp:expanded-list/ipi-bgp:action-value/ipi-bgp:value ";
            key "list-type expanded-type";
            description
                "bgp extended community expanded configurations";
            leaf list-type  {
                type  leafref {
                    path  "../config/list-type";
                }
                description "extcommunity Extended Community type";
            } // END of list-type definition.

            leaf expanded-type  {
                type  leafref {
                    path  "../config/expanded-type";
                }
                description "extcommunity Extended Community type";
            } // END of expanded-type definition.

            container config {
                description
                    "configuration parameters relating to bgp extended community expanded
                            list";
                uses bgp-extended-community-expanded-config;
            } // END of config-container definition.
            container state {
                config false;
                description
                    "state parameters relating to bgp extended community expanded list";
                uses bgp-extended-community-expanded-config;
            } // END of state-container definition.
            uses bgp-extended-community-expanded-action-value;
        } // End of expanded-list-list
    } // END of bgp-extended-community-expanded definition.
    grouping bgp-extended-community-list {
        description
            "extended bgp community configuration";
        container extended-community {
            description
                "main container for the complete extended community-list";
            uses bgp-extended-community-list-number;
            uses bgp-extended-community-standard;
            uses bgp-extended-community-expanded;
        } // END of extended-community-container definition.
    } // END of bgp-extended-community-list definition.
    grouping bgp-community {
        description
            "bgp community configuration";
        container community-lists {
            description
                "main container for the complete community-list";
            uses bgp-community-list-number;
            uses bgp-community-list-standard;
            uses bgp-community-list-expanded;
            uses bgp-extended-community-list;
        } // END of community-lists-container definition.
    } // END of bgp-community definition.
    grouping bgp-global-access-name-config {
        description
            "bgp global access name configuration";
        leaf access-list-name  {
            type  string {
                length "1..1965";
                pattern "[^?' =,>|]+";
            }
            description "Use this attribute to define a BGP Autonomous System (AS) path access
                        list. A named community list is a filter based on regular expressions.
                        If the regular expression matches the specified string representing
                        the AS path of the route, then the permit or deny condition applies.
                        Use this attribute to define the BGP access list globally.";
        } // END of access-list-name definition.

        leaf access-list-action  {
            type  ipi-bgp-types:bgp_community_list_action_t;
            description "Action type <0-1> 0 - Deny 1 - Permit";
        } // END of access-list-action definition.

        leaf access-list-regular-expression  {
            type  cml-data-types:cml_line_t {
                length "1..1965";
            }
            description "Regular expression to match BGP AS paths";
        } // END of access-list-regular-expression definition.

    } // END of bgp-global-access-name-config definition.
    grouping bgp-global-access-name-config-param {
        description
            "bgp global access name configuration";

        list as-path-access-list {
            key "access-list-name access-list-action access-list-regular-expression";
            description
                "bgp global access list configuration";
            leaf access-list-name  {
                type  leafref {
                    path  "../config/access-list-name";
                }
                description "Use this attribute to define a BGP Autonomous System (AS) path access
                            list. A named community list is a filter based on regular expressions.
                            If the regular expression matches the specified string representing
                            the AS path of the route, then the permit or deny condition applies.
                            Use this attribute to define the BGP access list globally.";
            } // END of access-list-name definition.

            leaf access-list-action  {
                type  leafref {
                    path  "../config/access-list-action";
                }
                description "Action type <0-1> 0 - Deny 1 - Permit";
            } // END of access-list-action definition.

            leaf access-list-regular-expression  {
                type  leafref {
                    path  "../config/access-list-regular-expression";
                }
                description "Regular expression to match BGP AS paths";
            } // END of access-list-regular-expression definition.

            container config {
                description
                    "configuration parameters relating to bgp access list";
                uses bgp-global-access-name-config;
            } // END of config-container definition.
            container state {
                config false;
                description
                    "state  parameters relating to bgp access list";
                uses bgp-global-access-name-config;
            } // END of state-container definition.
        } // End of as-path-access-list-list
    } // END of bgp-global-access-name-config-param definition.
    grouping bgp-mpls-6pe-config {
        description
            "bgp mpls 6pe configurations";
        leaf enable-per-prefix-label-mode  {
            type  empty;
            description "Use this attribute to configure mpls label mode";
        } // END of enable-per-prefix-label-mode definition.

    } // END of bgp-mpls-6pe-config definition.
    grouping bgp-mpls-6pe {
        description
            "bgp mpls 6pe configurations";
        container mpls-6pe {
            if-feature feature-list:HAVE_MPLS;
            if-feature feature-list:HAVE_6PE;
            description
                "Container for bgp mpls 6pe";
            container config {
                description
                    "configuration parameters relating to bgp mpls 6pe configurations";
                uses bgp-mpls-6pe-config;
            } // END of config-container definition.
            container state {
                config false;
                description
                    "state parameters relating to bgp mpls 6pe configurations";
                uses bgp-mpls-6pe-config;
            } // END of state-container definition.
        } // END of mpls-6pe-container definition.
    } // END of bgp-mpls-6pe definition.
    grouping bgp-global-debug-config {
        description
            "bgp global debug configurations";
        leaf debug-filter  {
            type  ipi-bgp-types:bgp_debug_type_t;
            description "Use this attribute to enable all BGP troubleshooting functions. Use
                        this attribute without any parameters to turn on normal bgp debug
                        information.";
        } // END of debug-filter definition.

        leaf debug-update-type  {
            type  ipi-bgp-types:bgp_update_debug_type_t;
            description "Use this attribute to enable all BGP troubleshooting functions. Use
                        this attribute without any parameters to turn on normal bgp debug
                        information.";
        } // END of debug-update-type definition.

    } // END of bgp-global-debug-config definition.
    grouping bgp-global-terminal-debug-state {
        description
            "Terminal debug status for bgp";
        leaf debug-options  {
            type  ipi-bgp-types:bgp_debug_type_t;
            description "Terminal debug option";
        } // END of debug-options definition.

        leaf updates-debug-options  {
            type  ipi-bgp-types:bgp_update_debug_type_t;
            description "Terminal debug update type option";
        } // END of updates-debug-options definition.

    } // END of bgp-global-terminal-debug-state definition.
    grouping bgp-global-debug {
        description
            "bgp global debug configurations";
        container debug {
            description
                "bgp global debug configurations";
            container config {
                description
                    "config parameters relating to  bgp global debug container";
                uses bgp-global-debug-config;
            } // END of config-container definition.
            container state {
                config false;
                description
                    "state parameters relating to  bgp global debug container";
                container terminal-debug-status {
                    config false;
                    description
                        "Terminal debug status";
                    uses bgp-global-terminal-debug-state;
                } // END of terminal-debug-status-container definition.
                uses bgp-global-debug-config;
            } // END of state-container definition.
        } // END of debug-container definition.
    } // END of bgp-global-debug definition.

    grouping  bgp-grouping {
    description
        "Top-level configuration and state for the BGP router";
    container bgp {
        description
            "Top-level configuration and state for the BGP router";
        container global {
            description
                "Global configuration for the BGP router uses bgp-global-base";
            uses bgp-global-common;
            uses bgp-community;
            uses bgp-global-access-name-config-param;
            uses bgp-mpls-l3-vpn;
            uses bgp-mpls-6pe;
            uses bgp-global-debug;
        } // END of global-container definition.
        uses bgp-instance-grouping;
    } // END of bgp-container definition.
    } // END of bgp-grouping definition.

    uses bgp-grouping;

    rpc clear-ip-bgp-all {
        description "clear all bgp instances and peer";
        input  {
            leaf afi  {
                type ipi-bgp-types:bgp_afi_type_t;
                mandatory true;
                description "BGP address family identifier";
            }
            leaf safi  {
                type ipi-bgp-types:bgp_rpc_safi_type_t;
                mandatory true;
                description "BGP sub address family identifier";
            }
            leaf clear-type  {
                type ipi-bgp-types:bgp_clear_type_t;
                mandatory true;
                description "BGP 'clear' Types";
            }
            leaf clear-soft  {
                type ipi-bgp-types:bgp_clear_soft_t;
                mandatory true;
                description "clear flag for peer soft, route flap dampening and table map";
            }
            leaf arg  {
                type ipi-bgp-types:bgp_hostname_t;
                mandatory true;
                description "input arguments (peer Address, prefix address, peer-group name, bgp
                            As)";
            }
        }
    }

    rpc clear-ip-bgp-all-peer {
        description "clear all bgp peers";
    }

    rpc clear-ip-bgp-all-peer-vrf {
        description "clear all bgp instances and peer in vrf(all|default)";
        input  {
            leaf vrf-name  {
                type string;
                mandatory true;
                description "vrf name";
            }
            leaf afi  {
                type ipi-bgp-types:bgp_afi_type_t;
                mandatory true;
                description "BGP address family identifier";
            }
            leaf safi  {
                type ipi-bgp-types:bgp_rpc_safi_type_t;
                mandatory true;
                description "BGP sub address family identifier";
            }
            leaf clear-type  {
                type ipi-bgp-types:bgp_clear_type_t;
                mandatory true;
                description "BGP 'clear' Types";
            }
            leaf clear-soft  {
                type ipi-bgp-types:bgp_clear_soft_t;
                mandatory true;
                description "clear flag for peer soft, route flap dampening and table map";
            }
            leaf address  {
                type ipi-bgp-types:bgp_hostname_t;
                mandatory true;
                description "input arguments (peer Address, prefix address, peer-group name, bgp
                            As)";
            }
        }
    }

    rpc clear-ip-bgp-all-vrf {
        description "clear all bgp instances and peer in specific vrf";
        input  {
            leaf vrf-name  {
                type string;
                mandatory true;
                description "vrf name";
            }
            leaf afi  {
                type ipi-bgp-types:bgp_afi_type_t;
                mandatory true;
                description "BGP address family identifier";
            }
            leaf safi  {
                type ipi-bgp-types:bgp_rpc_safi_type_t;
                mandatory true;
                description "BGP sub address family identifier";
            }
            leaf clear-type  {
                type ipi-bgp-types:bgp_clear_type_t;
                mandatory true;
                description "BGP 'clear' Types";
            }
            leaf clear-soft  {
                type ipi-bgp-types:bgp_clear_soft_t;
                mandatory true;
                description "clear flag for peer soft, route flap dampening and table map";
            }
            leaf address  {
                type ipi-bgp-types:bgp_hostname_t;
                mandatory true;
                description "input arguments (peer Address,prefix address, peer-group name, bgp As)";
            }
        }
    }

    rpc bgp-graceful-restart {
        description "Graceful restart of bgp";
    }

    rpc clear-bgp-statistics {
        description "clear all bgp peer Statistics fields";
    }

    rpc bgp-snmp-restart {
        description "restart SNMP in Border Gateway Protocol (BGP)";
    }

    rpc bgp-debug-on {
        description "Use this RPC to enable debug on BGP";
        input  {
            leaf debug-options  {
                type ipi-bgp-types:bgp_debug_type_t;
                mandatory true;
                description "Use this command to turn on all BGP troubleshooting functions. Use
                            this command without any parameters to turn on normal bgp debug
                            information..";
            }
        }
    }

    rpc bgp-debug-off {
        description "Use this RPC to disable debug on BGP";
        input  {
            leaf debug-options  {
                type ipi-bgp-types:bgp_debug_type_t;
                mandatory true;
                description "Use this command to turn off, BGP debugging at various levels.";
            }
        }
    }

    rpc bgp-debug-updates-type-on {
        description "Use this RPC to enable BGP update debug";
        input  {
            leaf debug-update-type  {
                type ipi-bgp-types:bgp_update_debug_type_t;
                mandatory true;
                description "Use this attribute to turn on debugging for BGP update";
            }
        }
    }

    rpc bgp-undebug {
        description "Use this RPC to disable debug on BGP.";
        input  {
            leaf undebug-options  {
                type ipi-bgp-types:bgp_debug_type_t;
                mandatory true;
                description "Use this command to turn off, BGP debugging at various levels.";
            }
        }
    }

    rpc bgp-all-debug-off {
        description "Use this RPC to disable debug on BGP.";
    }

    rpc bgp-all-undebug {
        description "Use this RPC to disable debug on BGP.";
    }

    notification bgp-established-notification {

        description "Notify BGP Peer established notification.";

        // eventClass "STATE";
        leaf peer-address {
            type ipi-bgp-types:bgp_ip_addr_t;
        description
            "Reference to the address of the BGP peer used as a key in the peer
                    list";
        }

        leaf bgp-as {
            type  uint32;
        description
            "Use this attribute to start a BGP process.";
        }

        leaf peer-state {
            type ipi-bgp-types:bgp_peer_status_t;
        description
            "Bgp peer session state. If there is change in state of the session ,
                    notification will be published only if the current state or the
                    previous state is in establised state";
        }
    }

    notification bgp-backward-transition-notification {

        description "Notify Peer State backward transition notification.";

        // eventClass "STATE";
        leaf peer-address {
            type ipi-bgp-types:bgp_ip_addr_t;
        description
            "Reference to the address of the BGP peer used as a key in the peer
                    list";
        }

        leaf bgp-as {
            type  uint32;
        description
            "Use this attribute to start a BGP process.";
        }

        leaf peer-state {
            type ipi-bgp-types:bgp_peer_status_t;
        description
            "Bgp peer session state. If there is change in state of the session ,
                    notification will be published only if the current state or the
                    previous state is in establised state";
        }
    }

}

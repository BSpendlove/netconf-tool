/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-efm.yang
*
*/

module ipi-efm {

    yang-version 1.1;

    namespace   "http://www.ipinfusion.com/yang/ocnos/ipi-efm";

    prefix "ipi-efm";

    import ipi-efm-types {
        prefix ipi-efm-types;
        revision-date 2020-07-27;
    }

    import ipi-interface {
        prefix ipi-interface;
        revision-date 2022-04-05;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for Ethernet OAM on interface";


    revision "2021-09-01" {
        description "Changed base interface module's switchport attribute name and the datatype from bool to empty";
        reference " 0.1.2.";
    }

    revision "2021-08-31" {
        description "Changed to link-monitor-off to make backend default and front-end matching";
        reference " 0.1.1.";
    }

    revision "2021-07-27" {
        description "Initial Version";
        reference " 0.1.0.";
    }

    grouping ethernet-oam-interface-config {
        description
            "Grouping for ethernet OAM config";
        leaf name  {
            type  leafref {
                path  "/ipi-interface:interfaces/ipi-interface:interface/ipi-interface:name";
            }
            description "Name of the interface on which to enable Ethernet OAM.";
        } // END of name definition.

        leaf enable  {
            type  empty;
            description "Enable Ethernet OAM on the interface";
        } // END of enable definition.

        leaf mode  {
            type  ipi-efm-types:ethernet_oam_mode_t;
            description "Ethernet OAM mode on the interface";
        } // END of mode definition.

        leaf link-lost-timeout  {
            type  uint8 {
                 range "2..30"  {
                    description "2..30:Time value (2-30)sec";
                 }
            }
            description "Ethernet OAM link lost timer related configs";
        } // END of link-lost-timeout definition.

        leaf pdu-min-rate  {
            type  uint8 {
                 range "1..10"  {
                    description "1..10:(1-10) seconds";
                 }
            }
            description "OAMPDU minimum rate per second";
        } // END of pdu-min-rate definition.

        leaf pdu-max-rate  {
            type  uint8 {
                 range "1..10"  {
                    description "1..10:(1-10) OAMPDUs per sec";
                 }
            }
            units "seconds";
            description "OAMPDU maximum rate per second";
        } // END of pdu-max-rate definition.

        leaf unidirectional-link-support  {
            type  empty;
            description "Ethernet OAM unidirectional link support on the interface";
        } // END of unidirectional-link-support definition.

        leaf remote-loopback-support  {
            type  empty;
            description "Ethernet OAM remote loopback support on the interface";
        } // END of remote-loopback-support definition.

        leaf remote-loopback-timeout  {
            type  uint8 {
                 range "1..10"  {
                    description "1..10:Timeout value (1-10) Secs";
                 }
            }
            description "Ethernet OAM remote loopback timeout on the interface";
        } // END of remote-loopback-timeout definition.

        leaf link-monitor-support  {
            type  empty;
            description "Ethernet OAM link monitor support on the interface";
        } // END of link-monitor-support definition.

        leaf link-monitor-off  {
            type  empty;
            description "Ethernet OAM link monitoring on the interface";
        } // END of link-monitor-off definition.

        leaf link-monitor-event-log-size  {
            type  uint8 {
                 range "1..100"  {
                    description "1..100:Log size (1-100)";
                 }
            }
            description "Ethernet OAM maximum event log entries on interface";
        } // END of link-monitor-event-log-size definition.

        leaf disable-port-on-critical-event-remote-failure  {
            type  empty;
            description "Ethernet OAM critical event remote failure action on interface";
        } // END of disable-port-on-critical-event-remote-failure definition.

        leaf disable-port-on-dying-gasp-remote-failure  {
            type  empty;
            description "Ethernet OAM dying gasp remote failure action on interface";
        } // END of disable-port-on-dying-gasp-remote-failure definition.

        leaf disable-port-on-link-fault-remote-failure  {
            type  empty;
            description "Ethernet OAM link fault remote failure action on interface";
        } // END of disable-port-on-link-fault-remote-failure definition.

        leaf remote-loopback-start  {
            type  empty;
            description "Ethernet OAM remote loopback trigger on interface";
        } // END of remote-loopback-start definition.

    } // END of ethernet-oam-interface-config definition.
    grouping ethernet-oam-interface-state {
        description
            "Grouping for ethernet OAM state on interface";
        leaf if-index  {
            type  uint32;
            config false;
            description "The internal interface index";
        } // END of if-index definition.

        leaf interface-state  {
            type  ipi-efm-types:ethernet_oam_oper_status_t;
            config false;
            description "The interface Ethernet OAM operational state";
        } // END of interface-state definition.

    } // END of ethernet-oam-interface-state definition.
    grouping ethernet-oam-debug-config {
        description
            "Grouping for ethernet OAM debug config";
        leaf debug-options  {
            type  ipi-efm-types:ethernet_oam_debug_type_t;
            description "Debugging enable configuration for Ethernet OAM";
        } // END of debug-options definition.

    } // END of ethernet-oam-debug-config definition.
    grouping ethernet-oam-terminal-debug-state {
        description
            "Grouping for ethernet OAM debug state";
        leaf terminal-debug-options  {
            type  ipi-efm-types:ethernet_oam_debug_type_t;
            description "Indicate current terminal debugging state for Ethernet OAM";
        } // END of terminal-debug-options definition.

    } // END of ethernet-oam-terminal-debug-state definition.
    grouping ethernet-oam-debug-top {
        description
            "Ethernet OAM debug configurations";
        container debug {
            description
                "The debug configuration data";
            container config {
                description
                    "configuration data for Ethernet OAM debug configuration";
                uses ethernet-oam-debug-config;
            } // END of config-container definition.
            container state {
                config false;
                description
                    "PON debug states";
                container terminal-debug-status {
                    config false;
                    description
                        "Terminal debug status";
                    uses ethernet-oam-terminal-debug-state;
                } // END of terminal-debug-status-container definition.
                uses ethernet-oam-debug-config;
            } // END of state-container definition.
        } // END of debug-container definition.
    } // END of ethernet-oam-debug-top definition.

    grouping  ethernet-oam-grouping {
    description
        "Top level container for Ethernet OAM (EFM)";
    container ethernet-oam {
        description
            "Top level container for Ethernet OAM (EFM)";
        container interfaces {
            description
                "Top level container for Ethernet OAM on each interface";

            list interface {
            when " /ipi-interface:interfaces/ipi-interface:interface/ipi-interface:config/ipi-interface:enable-switchport = '1' + /ipi-efm:ethernet-oam/ipi-efm:interfaces/ipi-efm:interface/ipi-efm:config/ipi-efm:enable = '1' ";
                key "name";
                description
                    "List of interfaces on which Ethernet OAM available";
                leaf name  {
                    type  leafref {
                        path  "../config/name";
                    }
                    description "Name of the interface on which to enable Ethernet OAM.";
                } // END of name definition.

                container config {
                    description
                        "configuration data for Ethernet OAM on interface";
                    uses ethernet-oam-interface-config;
                } // END of config-container definition.
                container state {
                    config false;
                    description
                        "Ethernet OAM config states";
                    uses ethernet-oam-interface-config;
                    uses ethernet-oam-interface-state;
                } // END of state-container definition.
            } // End of interface-list
        } // END of interfaces-container definition.
        uses ethernet-oam-debug-top;
    } // END of ethernet-oam-container definition.
    } // END of ethernet-oam-grouping definition.

    uses ethernet-oam-grouping;

    rpc efm-terminal-debug-on {
        description "Enable terminal debug for Ethernet OAM";
        input  {
            leaf terminal-debug-options  {
                type ipi-efm-types:ethernet_oam_debug_type_t;
                mandatory true;
                description "Debugging state for Ethernet OAM";
            }
        }
    }

    rpc efm-terminal-debug-off {
        description "Disable terminal debug for  Ethernet OAM";
        input  {
            leaf terminal-debug-options  {
                type ipi-efm-types:ethernet_oam_debug_type_t;
                mandatory true;
                description "Debugging state for Ethernet OAM";
            }
        }
    }

    rpc clear-interface-oam-counters {
        description "Use clear-interface-oam-counters to clear counters on specific
                    interface";
        input  {
            leaf name  {
                type string;
                mandatory true;
                description "Name of the interface to clear counters";
            }
        }
    }

}

/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-ssh-types.yang
*
*/

module ipi-ssh-types {

    yang-version 1.1;

    namespace   "http://www.ipinfusion.com/yang/ocnos/ipi-ssh-types";

    prefix "ipi-ssh-types";

    organization
        "IP Infusion Inc.";

    contact
        "Address: 3965 Freedom Circle, Suite 200, Santa Clara, CA 95054
         Phone: +1 408-400-1900
         E-mail: support@ipinfusion.com
         Web: http://www.ipinfusion.com/";

    description
        "SSH data types";


    revision "2021-09-03" {
        description "Update descriptions of attribute";
        reference " 0.3.0.";
    }

    revision "2021-08-02" {
        description "Added all-keys element to SSH_HOST_KEY_TYPE_T";
        reference " 0.2.0.";
    }

    revision "2021-07-14" {
        description "Initial Version";
        reference " 0.1.0.";
    }



    typedef  ssh_public_key_t {
        type string;
        description "type definition for SSH_PUBLIC_KEY_T";
    }

    typedef  ssh_ecdsa_key_len_t {
        type enumeration {
            enum 256 {
                value 256;
                description "256 bits";
            }
            enum 384 {
                value 384;
                description "384 bits";
            }
            enum 521 {
                value 521;
                description "521 bits";
            }
        }
        description "type definition for SSH_ECDSA_KEY_LEN_T";
    }

    typedef  ssh_host_key_type_t {
        type enumeration {
            enum all-keys {
                value 0;
                description "Clear all host keys";
            }
            enum dsa {
                value 1;
                description "DSA host key";
            }
            enum rsa {
                value 2;
                description "RSA host key";
            }
            enum ecdsa {
                value 3;
                description "ECDSA host key";
            }
            enum ed25519 {
                value 4;
                description "ED25519 host key";
            }
        }
        description "type definition for SSH_HOST_KEY_TYPE_T";
    }

}

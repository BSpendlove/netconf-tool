module ipi-oc-platform-types-deviations {
    namespace "http://www.ipinfusion.com/yang/ocnos/ipi-oc-platform-types-deviations";
    prefix "ipi-oc-platform-types-deviations";

    import openconfig-platform-types {
        prefix oc-platform-types;
    }

    revision "2021-01-29" {
        description
          "First release: add new identities that OcNOS supports";
    }

    identity NA {
        base oc-platform-types:COMPONENT_OPER_STATUS;
        description
          "Not Applicable";
    }

    identity HW_NA {
        base oc-platform-types:OPENCONFIG_HARDWARE_COMPONENT;
        description
          "Not Applicable";
    }

    identity POWER_RAIL {
        base oc-platform-types:OPENCONFIG_HARDWARE_COMPONENT;
        description
          "Power rail component";
    }

    identity FAN_TRAY {
        base oc-platform-types:OPENCONFIG_HARDWARE_COMPONENT;
        description
          "Fan tray component";
    }

    identity RAM {
        base oc-platform-types:OPENCONFIG_HARDWARE_COMPONENT;
        description
          "Ram Memory component";
    }

    identity PTP_CLOCK {
        base oc-platform-types:OPENCONFIG_HARDWARE_COMPONENT;
        description
          "PTP clock component";
    }
}

/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : zebm-cli.yang
*
*/



module zebm-cli {
    yang-version 1.1;
    namespace "http://ipinfusion.com/ns/zebmcli";

    prefix zebm-cli;

    organization
        "IP Infusion Inc.";

    contact
        "3965 Freedom Circle, Suite 200
        Santa Clara, CA 95054 +1 408-400-1900
        E-mail: support@ipinfusion.com
        Web: http://www.ipinfusion.com/";

    description "List of RPCs used for CML actions";


    revision "2022-01-13" {
        description "Added new RPC for user sessions clear.";
        reference "0.7.0";}

    revision "2021-12-27" {
        description "Added support for startup and candidate force-unlock.";
        reference "0.6.0";}

    revision "2021-12-01" {
        description "Added support for config change notification.";
        reference "0.5.0";}

    revision "2021-05-03" {
        description "Added support for import by revision-date.";
        reference "0.4.0";}

    revision "2021-02-02" {
        description "Add new RPC netconf-translation.";
        reference "0.3.0";}

    revision "2020-11-13" {
        description "Datamodel restructuring : revisied on 2020-11-13.";
        reference "0.2.0";}

    revision "2015-10-15" {
        description "initial version: revisied on 2015-10-15.";
        reference "0.1.0";}

    rpc netconf-translation {

        description "This RPC allows user to enable/disable NETCONF translation feature";
        input {
            leaf status {
                type enumeration {
                    enum disable {
                        description "disable NETCONF translation feature";
                    }
                    enum openconfig {
                        description "enable NETCONF OpenConfig translation";
                    }
                }
                description "Enable or disable NETCONF translation feature";
            }
        }
    }

    rpc force-unlock {

        description "This RPC allows user to forcefully unlock the config-store";
        input {
            leaf target {
                type enumeration {
                    enum running {
                    description "running config-store";
                     }
                    enum candidate {
                    description "candidate config-store";
                     }
                    enum startup {
                    description "startup config-store";
                     }
                }
                mandatory true;
                description "Type of config store";
            }
            leaf after {
                type uint32 {
                    range "0..600";
                }
                description "Number of seconds";
            }
        }
    }

    rpc set-transaction-limit {

        description "This RPC will allow user to set number of transactions allowed per commit";
        input {
            leaf transaction-limit {
                type uint32 {
                    range "0..300000";
                }
                mandatory true;
                description "Number of operation in single netconf transaction set 0 for no limit";
            }
        }
    }

    notification warning-notification {

        description "This RPC will display warning messages";
        leaf warningMsg {
            type string;
            mandatory true;
            description "warning string";
        }
    }

    rpc show-transaction-limit {
        description "This RPC will display the transaction limit per commit";
        output {
            leaf transaction-limit {
                type string;
                description " Displays number of transaction-limit";
            }
        }
    }

    rpc sys-reload {
        description "Halt and perform a cold restart";
        input {
            leaf save-config {
                type boolean;
                mandatory true;
                description "Copy running-config to startup-config";
            }
        }
    }

    rpc show-auto-config-sync-state {
        description "This RPC will display whether auto config sync is enabled or disabled.";
        output {
            leaf auto-config-sync-state {
                type string;
                description "Shows if auto config sync is enabled or disabled";
            }
        }
    }

    rpc auto-config-sync {
        description "This RPC will allow the user to enable or disable auto config sync";
        input {
            leaf status {
                type enumeration {
                    enum disable {
                        description "disable config auto sync";
                    }
                    enum enable {
                        description "enable config auto sync";
                    }
                }
                description "Enable or disable auto config sync. Once enabled config sync operation will be started whenever any configuration is performed";
            }
        }
    }

    rpc sync-running-config {
        description "This RPC will synchronize the database state with the running config";
    }

    rpc cml-config-sync-check {
        description "This RPC will check and inform if the running DB is in sync with running config";
    }

    rpc set-feature-netconf-status {
        description "Enable/Disable NetConf feature";
        input {
            leaf status {
                type enumeration {
                    enum disable {
                        value 0;
                        description "Disable netconf feature to restrict client to connect";
                    }
                    enum enable {
                        value 1;
                        description "Enable netconf feature to allow client to connect";
                    }
                }
                mandatory true;
                description "Provide input value to enable/disable feature";
            }
        }
    }

    rpc get-feature-netconf-status {
        description "This RPC will display the netconf feature status";
        output {
            leaf status {
                type enumeration {
                    enum disable {
                        value 0;
                        description "Disable netconf feature to restrict client to connect";
                    }
                    enum enable {
                        value 1;
                        description "Enable netconf feature to allow client to connect";
                    }
                }
                description "Leaf to display status of the feature";
            }
        }
    }

    rpc show-config-change-subscription {
        description "Check the status of config change notification subscription";
        output {
            leaf status {
                type string;
                description "holds subscription status";
            }
        }
    }

    rpc config-change-subscription {
        description "config change notification subscription";
        input {
            leaf status {
                type enumeration {
                    enum disable {
                        description "to disable subscription";
                    }
                    enum enable {
                        description "to enable subscription";
                    }
                }
                mandatory true;
                description "holds subscription status";
            }
        }
    }

    rpc clear-user-sessions {
        description "This RPC will clear all sessions of a specific user";
        input {
            leaf user-name {
                type string {
                    length "1..28";
                }
                mandatory true;
                description "The user name to which the session will be cleared";
            }
        }
    }

}

/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-bridge.yang
*
*/

module ipi-bridge {

    yang-version 1.1;

    namespace   "http://www.ipinfusion.com/yang/ocnos/ipi-bridge";

    prefix "ipi-bridge";

    import cml-data-types {
        prefix cml-data-types;
        revision-date 2022-04-04;
    }

    import ipi-bridge-types {
        prefix ipi-bridge-types;
        revision-date 2022-01-25;
    }

    import ipi-interface {
        prefix ipi-interface;
        revision-date 2022-04-05;
    }

    import ipi-network-instance {
        prefix ipi-network-instance;
        revision-date 2021-11-10;
    }

    import ipi-port-vlan-types {
        prefix ipi-port-vlan-types;
        revision-date 2022-05-06;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "Layer-2 bridge configurations";


    revision "2022-01-13" {
        description "Modified sub module";
        reference " 0.7.0.";
    }

    revision "2021-12-07" {
        description "Add dependent object for between bridge and DHCP snooping objects";
        reference " 0.6.1.";
    }

    revision "2021-11-16" {
        description "SKU compilation fixes";
        reference " 0.6.1.";
    }

    revision "2021-10-18" {
        description "Removed custom DB triggers";
        reference " 0.6.0.";
    }

    revision "2021-09-15" {
        description "Removing implicit-delete tags that were generated as warnings in zebm log";
        reference " 0.5.4.";
    }

    revision "2021-09-06" {
        description "Added custom error codes for bridge-ports interace";
        reference " 0.5.3.";
    }

    revision "2021-09-03" {
        description "sget support for Provider Bridging";
        reference " 0.5.2.";
    }

    revision "2021-09-01" {
        description "Changed base interface module's switchport attribute name and the datatype from bool to empty";
        reference " 0.5.1.";
    }

    revision "2021-08-01" {
        description "Restructured current Provider Bridging hierarchy to OpenConfig style.";
        reference " 0.5.0.";
    }

    revision "2021-04-27" {
        description "Data model changes done for JIRA-45490 ";
        reference " 0.4.3.";
    }

    revision "2021-04-08" {
        description "Data model changes done for ocmp-608";
        reference " 0.4.2.";
    }

    revision "2021-03-30" {
        description "Disabling YANG support for l2-protocol-destination-mac attribute";
        reference " 0.4.1.";
    }

    revision "2021-02-09" {
        description "JIRA-43764: dot1 encapsulation for switching and SVI routing";
        reference " 0.4.0.";
    }

    revision "2021-01-27" {
        description "Change to have descriptions for individual leafs";
        reference " 0.3.0.";
    }

    revision "2020-12-15" {
        description "Change to have data-types in lower case instead of camel case";
        reference " 0.2.0.";
    }

    revision "2018-06-21" {
        description "Initial Version";
        reference " 0.1.0.";
    }

    grouping bridge-config {
        description
            "Bridge configuration data";
        leaf protocol  {
            type  ipi-bridge-types:bridge_protocol_t;
            mandatory true;
            description "Bridge protocol type";
        } // END of protocol definition.

        leaf disable-dynamic-learning  {
            type  empty;
            description "Enable/Disable a bridge to learn station location information for an
                        instance.This helps in making forwarding decisions";
        } // END of disable-dynamic-learning definition.

        leaf l2-protocol-destination-mac  {
            if-feature feature-list:HAVE_PROVIDER_BRIDGE;
            type  cml-data-types:cml_mac_addr_t {
                length "1..1965";
            }
            default "0100.C2CD.CDD0";
            description "This attribute changes L2 protocol destination MAC";
        } // END of l2-protocol-destination-mac definition.

        leaf dot1q-encapsulation  {
            if-feature feature-list:HAVE_DUNE;
            type  empty;
            description "Configure to use encapsulated dot1q value for switching and routing by
                        bridge ports";
        } // END of dot1q-encapsulation definition.

    } // END of bridge-config definition.
    grouping bridge-interface-state {
        description
            "State data for each interface";
        leaf switchport-mode  {
            type  ipi-port-vlan-types:port_vlan_switch_port_mode_t;
            description "Attribute specifies default switchport mode";
        } // END of switchport-mode definition.

    } // END of bridge-interface-state definition.
    grouping bridge-interface-config {
        description
            "Configuration data for STP on each interface";
        leaf name  {
            type  leafref {
                path  "/ipi-interface:interfaces/ipi-interface:interface/ipi-interface:name";
            }
            description "The textual name of the interface";
        } // END of name definition.

        leaf spanning-tree-protocol-status  {
            type  ipi-bridge-types:bridge_spanningtree_enable_disable_t;
            description "Attribute specifies to enable/disable Spanning Tree Protocol on a
                        interface";
        } // END of spanning-tree-protocol-status definition.

    } // END of bridge-interface-config definition.
    grouping bridge-ports-top {
        description
            "Top level grouping for interface stp configuration and state data";
        container bridge-ports {
            description
                "Container for STP configuration and state data on each interface";

            list interface {
            when " /ipi-interface:interfaces/ipi-interface:interface/ipi-interface:name + /ipi-interface:interfaces/ipi-interface:interface/ipi-interface:config/ipi-interface:enable-switchport = '1' ";
                key "name";
                description
                    "List of interfaces on which spanning tree protocol is
                                enabled/available";
                leaf name  {
                    type  leafref {
                        path  "../config/name";
                    }
                    description "The textual name of the interface";
                } // END of name definition.

                container config {
                    description
                        "Configuration data for STP on each interface";
                    uses bridge-interface-config;
                } // END of config-container definition.
                container state {
                    config false;
                    description
                        "Operational state data";
                    uses bridge-interface-config;
                    uses bridge-interface-state;
                } // END of state-container definition.
            } // End of interface-list
        } // END of bridge-ports-container definition.
    } // END of bridge-ports-top definition.
    grouping fdb-entry-config {
        description
            "Configuration data for FDB MAC address";
        leaf interface-name  {
            // when " !ipi-port-vlan:port-vlan/port-security/config/mode ";
            type  leafref {
                path  "/ipi-interface:interfaces/ipi-interface:interface/ipi-interface:name";
            }
            mandatory true;
            description "The textual name of the interface";
        } // END of interface-name definition.

        leaf mac-address  {
            type  cml-data-types:cml_mac_addr_t {
                length "1..1965";
            }
            description "Use this attribute to configure the static forwarding table MAC entry
                        for the bridge";
        } // END of mac-address definition.

        leaf action  {
            type  ipi-bridge-types:bridge_discardforward_t;
            mandatory true;
            description "Use this attribute to configure fame discard/forward action for given
                        MAC address";
        } // END of action definition.

    } // END of fdb-entry-config definition.
    grouping static-mac-table-entry-top {
        description
            "Top level grouping for FDB  configuration and state data";

        list entry {
            key "mac-address";
            description
                "List of FDB MAC entries";
            leaf mac-address  {
                type  leafref {
                    path  "../config/mac-address";
                }
                description "Use this attribute to configure the static forwarding table MAC entry
                            for the bridge";
            } // END of mac-address definition.

            container config {
                description
                    "Configuration data for FDB MAC entries";
                uses fdb-entry-config;
            } // END of config-container definition.
            container state {
                config false;
                description
                    "Operational state data";
                uses fdb-entry-config;
            } // END of state-container definition.
        } // End of entry-list
    } // END of static-mac-table-entry-top definition.
    grouping static-mac-table-top {
        description
            "Top level grouping for FDB configuration and state data";
        container static-mac-table {
            description
                "MAC table information";
            uses static-mac-table-entry-top;
        } // END of static-mac-table-container definition.
    } // END of static-mac-table-top definition.
    grouping fdb-interface-config {
        description
            "Grouping for FDB MAC address entries";
        leaf interface-name  {
            type  leafref {
                path  "/ipi-interface:interfaces/ipi-interface:interface/ipi-interface:name";
            }
            description "The textual name of the interface";
        } // END of interface-name definition.

        leaf disable-mac-learning  {
            type  empty;
            mandatory true;
            description "Use this attribute to disable MAC learning on a interface";
        } // END of disable-mac-learning definition.

    } // END of fdb-interface-config definition.
    grouping fdb-interface-top {
        description
            "Top level grouping for interface FDB data";

        list interface {
            key "interface-name";
            description
                "List of FDB interface entries";
            leaf interface-name  {
                type  leafref {
                    path  "../config/interface-name";
                }
                description "The textual name of the interface";
            } // END of interface-name definition.

            container config {
                description
                    "Configuration data for FDB interface";
                uses fdb-interface-config;
            } // END of config-container definition.
            container state {
                config false;
                description
                    "Operational state data";
                uses fdb-interface-config;
            } // END of state-container definition.
        } // End of interface-list
    } // END of fdb-interface-top definition.
    grouping fdb-interfaces-top {
        description
            "Top level grouping for interface FDB data";
        container interfaces {
            description
                "MAC table information";
            uses fdb-interface-top;
        } // END of interfaces-container definition.
    } // END of fdb-interfaces-top definition.
    grouping dynamic-mac-table-entry-state {
        description
            "Dynamic learned MAC information";
        leaf mac-address  {
            type  cml-data-types:cml_mac_addr_t {
                length "1..1965";
            }
            description "Dynamic learned MAC address";
        } // END of mac-address definition.

        leaf vlan-id  {
            type  uint16;
            description "This attribute provides value for CVLAN ID in case of customer and
                        provider edge bridges and SVLAN ID in case of provider bridges";
        } // END of vlan-id definition.

        leaf svlan-id  {
            if-feature feature-list:HAVE_PROVIDER_BRIDGE;
            type  uint16;
            description "Service VLAN ID";
        } // END of svlan-id definition.

        leaf interface-name  {
            type  leafref {
                path  "/ipi-interface:interfaces/ipi-interface:interface/ipi-interface:name";
            }
            description "MAC learned interface";
        } // END of interface-name definition.

        leaf action  {
            type  ipi-bridge-types:bridge_discardforward_t;
            description "Frame discard/forward information for given MAC address";
        } // END of action definition.

        leaf entry-time-out  {
            type  uint32;
            units "seconds";
            description "The remaining time to delete entry for given MAC address from dynamic
                        MAC learned table";
        } // END of entry-time-out definition.

    } // END of dynamic-mac-table-entry-state definition.
    grouping dynamic-mac-table-entry-top {
        description
            "Top level group for dynamic learned MAC address information";

        list entry {
            if-feature feature-list:HAVE_HAL;
            key "mac-address vlan-id";
            config false;
            description
                "List of dynamic learned MAC entries";
            leaf mac-address  {
                type  leafref {
                    path  "../state/mac-address";
                }
                description "Dynamic learned MAC address";
            } // END of mac-address definition.

            leaf vlan-id  {
                type  leafref {
                    path  "../state/vlan-id";
                }
                description "This attribute provides value for CVLAN ID in case of customer and
                            provider edge bridges and SVLAN ID in case of provider bridges";
            } // END of vlan-id definition.

            container state {
                if-feature feature-list:HAVE_HAL;
                config false;
                description
                    "Dynamic learned information operational state data";
                uses dynamic-mac-table-entry-state;
            } // END of state-container definition.
        } // End of entry-list
    } // END of dynamic-mac-table-entry-top definition.
    grouping dynamic-mac-table-top {
        description
            "Top level grouping for FDB configuration and state data";
        container dynamic-mac-table {
            description
                "Dynamic MAC table information";
            uses dynamic-mac-table-entry-top;
        } // END of dynamic-mac-table-container definition.
    } // END of dynamic-mac-table-top definition.
    grouping fdb-top {
        description
            "Top level grouping FDB";
        container fdb {
            description
                "List of FDB MAC and interface entries";
            uses fdb-interfaces-top;
            uses static-mac-table-top;
            uses dynamic-mac-table-top;
        } // END of fdb-container definition.
    } // END of fdb-top definition.
    grouping evc-config {
        description
            "Grouping for ethernet virtual conneciton data";
        leaf id  {
            type  string {
                length "1..1965";
                pattern "[^?' =,>|]+";
            }
            description "Ethernet virtual conneciton ID";
        } // END of id definition.

        leaf maximum-uni  {
            type  uint32 {
                 range "1..32"  {
                    description "1..32:Maximum UNI number for the EVC/SVLAN";
                 }
            }
            mandatory true;
            description "Use this attribute to configure maximum UNI number for the given
                        EVC/SVLAN";
        } // END of maximum-uni definition.

    } // END of evc-config definition.
    grouping evc-top {
        description
            "Top level grouping for ethernet virtual conneciton configuration and
                        state data";
    } // END of evc-top definition.

    grouping  bridge-grouping {
    description
        "Bridge configuration and state data";
    container bridge {
        description
            "Bridge configuration and state data";
        container config {
            presence "Configure bridge protocol";
            description
                "Configuration data for bridge group";
            uses bridge-config;
        } // END of config-container definition.
        container state {
            config false;
            description
                "Operational state data";
            uses bridge-config;
        } // END of state-container definition.
        uses bridge-ports-top;
        uses fdb-top;
        uses evc-top;
    } // END of bridge-container definition.
    } // END of bridge-grouping definition.

    augment /ipi-network-instance:network-instances/ipi-network-instance:network-instance {
    when " /ipi-network-instance:network-instances/ipi-network-instance:network-instance/ipi-network-instance:instance-type = 'l2ni' + /ipi-network-instance:network-instances/ipi-network-instance:network-instance/ipi-bridge:bridge/ipi-bridge:config/ipi-bridge:protocol ";
        description
            "Bridge configuration and state data";
        uses bridge-grouping;
    }


}

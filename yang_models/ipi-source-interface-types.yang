/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-source-interface-types.yang
*
*/

module ipi-source-interface-types {

    yang-version 1.1;

    namespace   "http://www.ipinfusion.com/yang/ocnos/ipi-source-interface-types";

    prefix "ipi-source-interface-types";

    organization
        "IP Infusion Inc.";

    contact
        "Address: 3965 Freedom Circle, Suite 200, Santa Clara, CA 95054
         Phone: +1 408-400-1900
         E-mail: support@ipinfusion.com
         Web: http://www.ipinfusion.com/";

    description
        "Source Interface types";


    revision "2021-08-27" {
        description "Initial version";
        reference "Initial Version";
    }



    typedef  src_intf_status_t {
        type enumeration {
            enum disable {
                value 0;
                description "Source Interface Disable";
            }
            enum enable {
                value 1;
                description "Source Interface Enable";
            }
        }
        description "type definition for SRC_INTF_STATUS_T";
    }

    typedef  src_intf_proto_types_t {
        type enumeration {
            enum tacacs+ {
                value 49;
                description "Protocol TACACS+";
            }
            enum ntp {
                value 123;
                description "Protocol NTP";
            }
            enum snmp {
                value 161;
                description "Protocol SNMP";
            }
            enum syslog {
                value 514;
                description "Protocol Rsyslog";
            }
            enum radius {
                value 1812;
                description "Protocol RADIUS";
            }
        }
        description "type definition for SRC_INTF_PROTO_TYPES_T";
    }

}

/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-port-mirror-types.yang
*
*/

module ipi-port-mirror-types {

    yang-version 1.1;

    namespace   "http://www.ipinfusion.com/yang/ocnos/ipi-port-mirror-types";

    prefix "ipi-port-mirror-types";

    organization
        "IP Infusion Inc.";

    contact
        "Address: 3965 Freedom Circle, Suite 200, Santa Clara, CA 95054
         Phone: +1 408-400-1900
         E-mail: support@ipinfusion.com
         Web: http://www.ipinfusion.com/";

    description
        "Datatypes related to Port Mirroring";


    revision "2022-01-13" {
        description "Added if-feature for data types";
        reference " 0.2.0.";
    }

    revision "2021-11-16" {
        description "Initial Version";
        reference " 0.1.0.";
    }



    typedef  pmirror_mac_addr_t {
        type string {
            pattern "[0-9A-F]{4}\\.[0-9A-F]{4}\\.[0-9A-F]{4}";
        }
        description "type definition for PMIRROR_MAC_ADDR_T";
    }

    typedef  pmirror_sess_type_t {
        type enumeration {
            enum local {
                value 1;
                description "Create a local session";
            }
            enum remote {
                value 2;
                description "Create a remote source node session";
            }
        }
        description "type definition for PMIRROR_SESS_TYPE_T";
    }

    typedef  pmirror_dir_t {
        type enumeration {
            enum rx {
                value 1;
                description "Ingress";
            }
            enum tx {
                value 2;
                description "Egress";
            }
            enum both {
                value 3;
                description "Both";
            }
        }
        description "type definition for PMIRROR_DIR_T";
    }

    typedef  pmirror_ether_type_val_t {
        type enumeration {
            enum ipv4 {
                value 2048;
                description "Specify frame type as IPv4. Ethertype 0x0800";
            }
            enum arp {
                value 2054;
                description "Specify frame type as ARP. Ethertype 0x806";
            }
            enum ipv6 {
                value 34525;
                description "Specify frame type as IPv6. Ethertype 0x86dd";
            }
        }
        description "type definition for PMIRROR_ETHER_TYPE_VAL_T";
    }

    typedef  pmirror_ether_hex_val_string_t {
        type string;
        description "type definition for PMIRROR_ETHER_HEX_VAL_STRING_T";
    }

    typedef  pmirror_ethertype_t {
        type union {
            type pmirror_ether_type_val_t {

            }
            type pmirror_ether_hex_val_string_t {

            }
        }
        description "type definition for PMIRROR_ETHERTYPE_T";
    }

    typedef  pmirror_arp_type_t {
        type enumeration {
            enum req {
                value 1;
                description "Match ARP request packets";
            }
            enum resp {
                value 2;
                description "Match ARP response packets";
            }
        }
        description "type definition for PMIRROR_ARP_TYPE_T";
    }

    typedef  pmirror_alt_dir_t {
        type enumeration {
            enum receive {
                value 1;
                description "Mirror received traffic";
            }
            enum transmit {
                value 2;
                description "Mirror transmit traffic";
            }
            enum both {
                value 3;
                description "Mirror traffic in both directions";
            }
        }
        description "type definition for PMIRROR_ALT_DIR_T";
    }

}

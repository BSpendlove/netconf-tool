/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-acl-common.yang
*
*/

module ipi-acl-common {

    yang-version 1.1;

    namespace   "http://www.ipinfusion.com/yang/ocnos/ipi-acl-common";

    prefix "ipi-acl-common";

    import ipi-acl-types {
        prefix ipi-acl-types;
        revision-date 2022-01-20;
    }

    import ietf-yang-types {
        prefix yang;
        revision-date 2013-07-15;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "Common groupings in ipi-acl, ipi-acl-ipv6, ipi-acl-mac, ipi-acl-arp
                modules";


    revision "2021-09-17" {
        description "Moved 'destination-mac-options' from ipi-acl-common to ipi-acl-mac and ipi-acl-arp modules";
        reference " 0.3.0.";
    }

    revision "2021-09-03" {
        description "Update descriptions of attribute";
        reference " 0.2.0.";
    }

    revision "2021-07-14" {
        description "Restructured module as per OpenConfig style";
        reference " 0.1.0.";
    }

    grouping acl-tcp-config {
        description
            "Configuration data specific for TCP ACL entry";
        leaf protocol-tcp  {
            type  empty;
            mandatory true;
            description "Use this attribute to indicate that protocol carried in the IP packet
                        is tcp.";
        } // END of protocol-tcp definition.

        leaf tcp-source-port  {
            type  ipi-acl-types:acl_tcp_src_port_t;
            description "Use this attribute to set TCP Source port";
        } // END of tcp-source-port definition.

        leaf tcp-destination-port  {
            type  ipi-acl-types:acl_tcp_dest_port_t;
            description "Use this attribute to set TCP Destination port";
        } // END of tcp-destination-port definition.

    } // END of acl-tcp-config definition.
    grouping acl-udp-config {
        description
            "Configuration data specific for UDP ACL entry";
        leaf protocol-udp  {
            type  empty;
            mandatory true;
            description "Use this attribute to indicate that protocol carried in the IP packet
                        is udp.";
        } // END of protocol-udp definition.

        leaf udp-source-port  {
            type  ipi-acl-types:acl_udp_src_port_t;
            description "Use this attribute to set UDP Source port";
        } // END of udp-source-port definition.

        leaf udp-destination-port  {
            type  ipi-acl-types:acl_udp_dest_port_t;
            description "Use this attribute to set UDP destination port";
        } // END of udp-destination-port definition.

    } // END of acl-udp-config definition.
    grouping acl-fragments-config {
        description
            "Fragments action configuration attributes";
        leaf fragment-forwarding-action  {
            if-feature feature-list:HAVE_CUSTOM1_ACL;
            type  ipi-acl-types:acl_fragment_forwarding_action_t;
            mandatory true;
            description "Use this attribute to set forwarding action for IP fragments";
        } // END of fragment-forwarding-action definition.

        leaf fragment-monitor-action  {
            if-feature feature-list:HAVE_SFLOW;
            if-feature feature-list:HAVE_CUSTOM1_ACL;
            type  ipi-acl-types:acl_monitor_action_t;
            description "Use this attribute to enable logging or sampling of the packets on
                        which the match occurred (in-direction only).";
        } // END of fragment-monitor-action definition.

    } // END of acl-fragments-config definition.
    grouping acl-common-config {
        description
            "Common configuration data for IPv4, IPv6, MAC, ARP ACL entries";
        leaf forwarding-action  {
            type  ipi-acl-types:acl_forwarding_action_t;
            mandatory true;
            description "Specifies the forwarding action.  One forwarding action must be
                        specified for each ACL entry.";
        } // END of forwarding-action definition.

        leaf vlan-id  {
            type  uint16 {
                 range "1..4094"  {
                    description "1..4094:vlan  <1-4094>";
                 }
            }
            description "Use this attribute to set the vlan-id";
        } // END of vlan-id definition.

        leaf monitor-action  {
            if-feature feature-list:HAVE_SFLOW;
            if-feature feature-list:HAVE_CUSTOM1_ACL;
            type  ipi-acl-types:acl_monitor_action_t;
            description "Use this attribute to enable logging or sampling of the packets on
                        which the match occurred (in-direction only).";
        } // END of monitor-action definition.

    } // END of acl-common-config definition.
    grouping acl-ip-config {
        description
            "Common configuration data for IPv4, IPv6 ACL entries";
        leaf source-port-operator  {
            type  ipi-acl-types:acl_src_port_operations_t;
            description "Use this attribute to set the operator to be applied on the
                        source-port";
        } // END of source-port-operator definition.

        leaf lower-source-port-in-range  {
            type  uint16 {
                 range "0..65535"  {
                    description "0..65535:Lowest value in the range";
                 }
            }
            description "Use this attribute to set the lower boundary for source port range";
        } // END of lower-source-port-in-range definition.

        leaf upper-source-port-in-range  {
            type  uint16 {
                 range "0..65535"  {
                    description "0..65535:Highest value in the range";
                 }
            }
            description "Use this attribute to set the upper boundary for source port range";
        } // END of upper-source-port-in-range definition.

        leaf destination-port-operator  {
            type  ipi-acl-types:acl_dest_port_operations_t;
            description "Use this attribute to set the operator to be applied on the
                        destination-port";
        } // END of destination-port-operator definition.

        leaf lower-destination-port-in-range  {
            type  uint16 {
                 range "0..65535"  {
                    description "0..65535:Lowest value in the range";
                 }
            }
            description "Use this attribute to set the lower boundary for destination port
                        range";
        } // END of lower-destination-port-in-range definition.

        leaf upper-destination-port-in-range  {
            type  uint16 {
                 range "0..65535"  {
                    description "0..65535:Highest value in the range";
                 }
            }
            description "Use this attribute to set the upper boundary for destination port
                        range";
        } // END of upper-destination-port-in-range definition.

        leaf redirect-interface-name  {
            if-feature feature-list:HAVE_CUSTOM1_ACL;
            type  string {
                length "1..1965";
                pattern "[^?' =,>|]+";
            }
            description "Use this attribute to set the interface name on which packet to be
                        redirected (in-direction only)";
        } // END of redirect-interface-name definition.

        leaf fragments  {
            if-feature feature-list:HAVE_CUSTOM1_ACL;
            type  empty;
            description "Use this attribute to enable specialized fragmented packet-handling
                        behavior. In general, noninitial fragments that match the Layer 3
                        properties are affected by the permit or deny statement of the matched
                        entry. Enabling 'fragments' can enable ACLs to either deny or permit
                        noninitial fragments with more granularity.";
        } // END of fragments definition.

    } // END of acl-ip-config definition.
    grouping acl-mac-arp-config {
        description
            "Common configuration data for MAC, ARP ACL entries";
        leaf inner-vlan-id  {
            type  uint16 {
                 range "1..4094"  {
                    description "1..4094:vlan  <1-4094>";
                 }
            }
            description "Use this attribute to set the inner-vlan-id";
        } // END of inner-vlan-id definition.

        choice source-mac-options {
            description
                "Source mac options";
            case any-mac {

                description
                    "Any source address";

                leaf source-mac-any  {
                    type  empty;
                    description "Use this attribute to indicate any source address.";
                } // END of source-mac-any definition.

            }
            case host-mac {

                description
                    "Host Mac Address";

                leaf source-mac-host  {
                    type  ipi-acl-types:acl_mac_addr_t {
                        length "1..1965";
                    }
                    description "Use this attribute to set Host source address.";
                } // END of source-mac-host definition.

            }
            case mac-with-mask {

                description
                    "Mac address with mask";

                leaf source-mac-address  {
                    type  ipi-acl-types:acl_mac_addr_t {
                        length "1..1965";
                    }
                    description "Use this attribute to set source mac-address.";
                } // END of source-mac-address definition.

                leaf source-mac-mask  {
                    type  ipi-acl-types:acl_mac_addr_t {
                        length "1..1965";
                    }
                    description "Use this attribute to set source wildcard mask.";
                } // END of source-mac-mask definition.

            }
        } // END of source-mac-options-choice definition.
    } // END of acl-mac-arp-config definition.
    grouping acl-counters {
        description
            "ACL entry counters";
        leaf matched-packets  {
            type  yang:counter64;
            config false;
            description "The number of packets that matched the acl-entry on the attached
                        interface.";
        } // END of matched-packets definition.

    } // END of acl-counters definition.


}

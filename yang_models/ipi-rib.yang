/*
* Copyright (C) 2019 IP Infusion, Inc.
*  All Rights Reserved.
*
*** Auto generated by zebmdc

* Unless required by applicable law or agreed to in writing,
* software distributed under the License is distributed on an
* "AS IS" BASIS, WITHOUT WARRANTIES OR CONDITIONS OF ANY
* KIND, either express or implied.

* File name : ipi-rib.yang
*
*/

module ipi-rib {

    yang-version 1.1;

    namespace   "http://www.ipinfusion.com/yang/ocnos/ipi-rib";

    prefix "ipi-rib";

    import ipi-rib-types {
        prefix ipi-rib-types;
        revision-date 2021-09-03;
    }

    import ipi-interface {
        prefix ipi-interface;
        revision-date 2022-04-05;
    }

    import ipi-rib-common {
        prefix ipi-rib-common;
        revision-date 2021-12-08;
    }

    import ietf-inet-types {
        prefix inet;
        revision-date 2013-07-15;
    }

    import feature-list {
        prefix feature-list;
        revision-date 2022-07-13;
    }

    organization
        "IP Infusion Inc.";

    contact
        "Address: 3965 Freedom Circle, Suite 200, Santa Clara, CA 95054
         Phone: +1 408-400-1900
         E-mail: support@ipinfusion.com
         Web: http://www.ipinfusion.com/";

    description
        "Datamodel for RIB object";


    revision "2022-04-22" {
        description "Suncom patch merge";
        reference " 0.9.0.";
    }

    revision "2022-03-31" {
        description "Added IPV6 feature flag in needed areas";
        reference " 0.8.0.";
    }

    revision "2021-12-08" {
        description "Added new attribute track-id to support releated to object-tracking feature";
        reference " 0.7.0.";
    }

    revision "2021-11-16" {
        description "Added some if-feature to fix customer SKU compilation";
        reference " 0.6.0.";
    }

    revision "2021-09-01" {
        description "Changed base interface module's switchport attribute name and the datatype from bool to empty";
        reference " 0.5.0.";
    }

    revision "2021-03-15" {
        description "Removed configuration of Interface name as nexthop for ipv6 mroute commands";
        reference " 0.4.0.";
    }

    revision "2021-01-27" {
        description "Mroute related changes, added description for RPCs";
        reference " 0.3.0.";
    }

    revision "2020-12-15" {
        description "Change to have data-types in lower case instead of camel case";
        reference " 0.2.0.";
    }

    revision "2020-09-07" {
        description "Datamodel restructuring";
        reference " 0.1.0.";
    }

    grouping rib-global-config {
        description
            "Global configuration data for RIB";
        leaf fib-retain  {
            if-feature feature-list:HAVE_L3;
            type  ipi-rib-types:rib_fib_retain_t;
            units "seconds";
            default "60";
            description "Use this attribute to configure retain time for stale routes (forever
                        or specific time in seconds) in FIB after RIB restarts";
        } // END of fib-retain definition.

        leaf max-ecmp-paths  {
            if-feature feature-list:HAVE_MULTIPATH;
            type  uint8 {
                 range "1..64"  {
                    description "1..64:supported multipath numbers";
                 }
            }
            default "8";
            description "Use this attribute to set the maximum number of paths to install in
                        the FIB (Forwarding Information Base) for the ECMP (Equal-Cost
                        MultiPath) feature.";
        } // END of max-ecmp-paths definition.

        leaf max-static-routes  {
            type  uint32 {
                 range "1..4294967294"  {
                    description "1..4294967294:Allowed number of static routes";
                 }
            }
            default "4294967294";
            description "Use this attribute to set the maximum number of static routes.";
        } // END of max-static-routes definition.

        leaf max-fib-routes  {
            type  uint32 {
                 range "1..16384"  {
                    description "1..16384:Allowed number of fib routes including Kernel, Connect and
                            Static";
                 }
            }
            description "Use this attribute to set the maximum number of FIB (Forwarding
                        Information Base) routes excluding kernel, connected, and static
                        routes.";
        } // END of max-fib-routes definition.

    } // END of rib-global-config definition.
    grouping rib-debug-config {
        description
            "Debug configuration data for RIB";
        leaf debug-rib-options  {
            type  ipi-rib-types:rib_conf_debug_type_t;
            description "Use this attribute to debug the ribd process.";
        } // END of debug-rib-options definition.

        leaf debug-ipv4-routing-options  {
            type  ipi-rib-types:rib_debug_routing_type_t;
            description "Use this attribute to debug ip route.";
        } // END of debug-ipv4-routing-options definition.

        leaf debug-ipv6-routing-options  {
            type  ipi-rib-types:rib_debug_routing_type_t;
            description "Use this attribute to debug ipv6 route.";
        } // END of debug-ipv6-routing-options definition.

    } // END of rib-debug-config definition.
    grouping terminal-debug-state {
        description
            "Terminal debug status for RIB";
        leaf debug-rib-status  {
            type  ipi-rib-types:rib_debug_type_t;
            description "Terminal debug option";
        } // END of debug-rib-status definition.

        leaf debug-ip-routing-status  {
            type  ipi-rib-types:rib_debug_routing_type_t;
            description "Terminal debug ipv4 routing option";
        } // END of debug-ip-routing-status definition.

        leaf debug-ipv6-routing-status  {
            type  ipi-rib-types:rib_debug_routing_type_t;
            description "Terminal debug ipv6 routing option";
        } // END of debug-ipv6-routing-status definition.

    } // END of terminal-debug-state definition.
    grouping rib-ipv4-gateway-config {
        description
            "Configuration attributes for ipv4 static route with gateway address";
        leaf destination-prefix  {
            type  inet:ipv4-prefix;
            description "IP destination prefix (e.g. 10.0.0.0/8)";
        } // END of destination-prefix definition.

        leaf gateway-address  {
            type  inet:ipv4-address;
            description "Use this attribute to configure IP gateway address for  IPv4 static
                        route.";
        } // END of gateway-address definition.

        uses ipi-rib-common:rib-attr-config;
    } // END of rib-ipv4-gateway-config definition.
    grouping rib-ipv4-interface-config {
        description
            "Configuration attributes for static routes with interface";
        leaf destination-prefix  {
            type  inet:ipv4-prefix;
            description "IP destination prefix (e.g. 10.0.0.0/8)";
        } // END of destination-prefix definition.

        leaf interface-name  {
            type  string {
                length "1..1965";
                pattern "[^?' =,>|]+";
            }
            description "Use this attribute to create an IPv4 static route where nexthop is
                        interface name.";
        } // END of interface-name definition.

        uses ipi-rib-common:rib-attr-config;
    } // END of rib-ipv4-interface-config definition.
    grouping rib-ipv4-gateway-interface-config {
        description
            "Configuration attributes for static routes with gw and interface";
        leaf destination-prefix  {
            type  inet:ipv4-prefix;
            description "IP destination prefix (e.g. 10.0.0.0/8)";
        } // END of destination-prefix definition.

        leaf gateway-address  {
            type  inet:ipv4-address;
            description "Use this attribute to configure IP gateway address for  IPv4 static
                        route.";
        } // END of gateway-address definition.

        leaf interface-name  {
            type  string {
                length "1..1965";
                pattern "[^?' =,>|]+";
            }
            description "Use this attribute to create an IPv4 static route where nexthop is
                        interface name.";
        } // END of interface-name definition.

    } // END of rib-ipv4-gateway-interface-config definition.
    grouping rib-ipv6-gateway-config {
        description
            "Configuration attributes for ipv6 static routes";
        leaf destination-prefix  {
            type  inet:ipv6-prefix;
            description "IPv6 destination prefix (e.g. 3ffe:506::/32)";
        } // END of destination-prefix definition.

        leaf gateway-address  {
            type  inet:ipv6-address;
            description "Use this attribute to create an IPv6 static route for a subnet.";
        } // END of gateway-address definition.

        leaf distance  {
            type  uint32 {
                 range "1..255"  {
                    description "1..255:Distance value for this prefix";
                 }
            }
            default "1";
            description "Use this attribute to set distance value for the ipv6 route.";
        } // END of distance definition.

        leaf track-id  {
            if-feature feature-list:HAVE_OBJ_TRACKING;
            type  uint16 {
                 range "1..500"  {
                    description "1..500:Object Tracking id";
                 }
            }
            description "Use this attribute to track a object.";
        } // END of track-id definition.

    } // END of rib-ipv6-gateway-config definition.
    grouping rib-ipv6-interface-config {
        description
            "Configuration attributes for ipv6 static routes with interface";
        leaf destination-prefix  {
            type  inet:ipv6-prefix;
            description "IPv6 destination prefix (e.g. 3ffe:506::/32)";
        } // END of destination-prefix definition.

        leaf interface-name  {
            type  string {
                length "1..1965";
                pattern "[^?' =,>|]+";
            }
            description "Use this attribute to create an IPv6 static route where nexthop is
                        interface name.";
        } // END of interface-name definition.

        leaf distance  {
            type  uint32 {
                 range "1..255"  {
                    description "1..255:Distance value for this prefix";
                 }
            }
            default "1";
            description "Use this attribute to set distance value for the ipv6 route.";
        } // END of distance definition.

        leaf track-id  {
            if-feature feature-list:HAVE_OBJ_TRACKING;
            type  uint16 {
                 range "1..500"  {
                    description "1..500:Object Tracking id";
                 }
            }
            description "Use this attribute to track a object.";
        } // END of track-id definition.

    } // END of rib-ipv6-interface-config definition.
    grouping rib-ipv6-gateway-interface-config {
        description
            "Configuration attributes for ipv6 static routes with gateway and
                        interface name";
        leaf destination-prefix  {
            type  inet:ipv6-prefix;
            description "IPv6 destination prefix (e.g. 3ffe:506::/32)";
        } // END of destination-prefix definition.

        leaf gateway-address  {
            type  inet:ipv6-address;
            description "IPv6 gateway address";
        } // END of gateway-address definition.

        leaf interface-name  {
            type  leafref {
                path  "/ipi-interface:interfaces/ipi-interface:interface/ipi-interface:name";
            }
            description "Use this attribute to create an IPv6 static route where nexthop is
                        interface name and ipv6 prefix.";
        } // END of interface-name definition.

        leaf distance  {
            type  uint32 {
                 range "1..255"  {
                    description "1..255:Distance value for this prefix";
                 }
            }
            default "1";
            description "Use this attribute to set distance value for the ipv6 route with
                        nexthop as interface name and ipv6 prefix.";
        } // END of distance definition.

        leaf track-id  {
            if-feature feature-list:HAVE_OBJ_TRACKING;
            type  uint16 {
                 range "1..500"  {
                    description "1..500:Object Tracking id";
                 }
            }
            description "Use this attribute to track a object.";
        } // END of track-id definition.

    } // END of rib-ipv6-gateway-interface-config definition.
    grouping rib-bfd-config {
        description
            "Configuration attributes related to bfd for static routes";
        leaf bfd-state  {
            if-feature feature-list:HAVE_BFD;
            type  ipi-rib-types:rib_static_bfd_enable_disable_t;
            description "Use this attribute to set fall-over detection.";
        } // END of bfd-state definition.

    } // END of rib-bfd-config definition.
    grouping rib-interface-bfd-config {
        description
            "Interface level Configuration attributes related to BFD";
        leaf ipv4-enable-bfd  {
            if-feature feature-list:HAVE_BFD;
            type  ipi-rib-types:rib_bfd_state;
            description "Use this attribute to enable or disable Bidirectional Forwarding
                        Detection static routes.";
        } // END of ipv4-enable-bfd definition.

        leaf ipv6-enable-bfd  {
            if-feature feature-list:HAVE_BFD;
            if-feature feature-list:HAVE_IPV6;
            type  ipi-rib-types:rib_bfd_state;
            description "Use this attribute to enable or disable Bidirectional Forwarding
                        Detection static routes.";
        } // END of ipv6-enable-bfd definition.

    } // END of rib-interface-bfd-config definition.

    grouping  routing-grouping {
    description
        "RIB Master for system wide configurations";
    container routing {
        description
            "RIB Master for system wide configurations";
        container global {
            description
                "RIB global configurations";
            container config {
                description
                    "RIB global configuration attributes";
                uses ipi-rib-common:rib-global-bfd-config;
                uses rib-global-config;
            } // END of config-container definition.
            container state {
                config false;
                description
                    "Global Operational data for RIB";
                uses ipi-rib-common:rib-global-bfd-config;
                uses rib-global-config;
            } // END of state-container definition.
        } // END of global-container definition.
        container debug {
            description
                "RIB debug configurations";
            container config {
                description
                    "Debug related configuration attributes in RIB";
                uses rib-debug-config;
            } // END of config-container definition.
            container state {
                config false;
                description
                    "Operational data related to debug for RIB";
                container terminal-debug-status {
                    config false;
                    description
                        "Terminal debug status";
                    uses terminal-debug-state;
                } // END of terminal-debug-status-container definition.
                uses rib-debug-config;
            } // END of state-container definition.
        } // END of debug-container definition.
        container static-routes {
            description
                "Static Route configurations";
            container ipv4 {
                description
                    "IPV4 Static Route configurations";

                list route-vrf {
                    key "destination-prefix gateway-address interface-name";
                    description
                        "IPV4 static route config with gateway and interface";
                    leaf destination-prefix  {
                        type  leafref {
                            path  "../config/destination-prefix";
                        }
                        description "IP destination prefix (e.g. 10.0.0.0/8)";
                    } // END of destination-prefix definition.

                    leaf gateway-address  {
                        type  leafref {
                            path  "../config/gateway-address";
                        }
                        description "Gateway address to create an IPv4 static route.";
                    } // END of gateway-address definition.

                    leaf interface-name  {
                        type  leafref {
                            path  "/ipi-interface:interfaces/ipi-interface:interface/ipi-interface:name";
                        }
                        description "Use this attribute to create an IPv4 static route where nexthop is
                                    interface name.";
                    } // END of interface-name definition.

                    container config {
                        description
                            "configuration attributes for IPV4 static route with gateway and
                                    interface";
                        uses rib-ipv4-gateway-interface-config;
                    } // END of config-container definition.
                    container state {
                        config false;
                        description
                            "Operational data for IPV4 static route with gateway and interface";
                        uses rib-ipv4-gateway-interface-config;
                    } // END of state-container definition.
                } // End of route-vrf-list

                list route {
                    key "destination-prefix gateway-address";
                    description
                        "IPV4 static route config with gateway";
                    leaf destination-prefix  {
                        type  leafref {
                            path  "../config/destination-prefix";
                        }
                        description "IP destination prefix (e.g. 10.0.0.0/8)";
                    } // END of destination-prefix definition.

                    leaf gateway-address  {
                        type  leafref {
                            path  "../config/gateway-address";
                        }
                        description "Gateway address to create an IPv4 static route.";
                    } // END of gateway-address definition.

                    container config {
                        description
                            "configuration attributes for IPV4 static route with gateway";
                        uses rib-bfd-config;
                        uses rib-ipv4-gateway-config;
                    } // END of config-container definition.
                    container state {
                        config false;
                        description
                            "Operational data for IPV4 static route with gateway";
                        uses rib-bfd-config;
                        uses rib-ipv4-gateway-config;
                    } // END of state-container definition.
                } // End of route-list

                list interface-route {
                when " /ipi-interface:interfaces/ipi-interface:interface/ipi-interface:config/ipi-interface:enable-switchport != '1' ";
                    key "destination-prefix interface-name";
                    description
                        "IPV4 static route with interface name";
                    leaf destination-prefix  {
                        type  leafref {
                            path  "../config/destination-prefix";
                        }
                        description "IP destination prefix (e.g. 10.0.0.0/8)";
                    } // END of destination-prefix definition.

                    leaf interface-name  {
                        type  leafref {
                            path  "../config/interface-name";
                        }
                        description "Use this attribute to create an IPv4 static route where nexthop is
                                    interface name.";
                    } // END of interface-name definition.

                    container config {
                        description
                            "configuration attributes for static route with interface name";
                        uses rib-ipv4-interface-config;
                    } // END of config-container definition.
                    container state {
                        config false;
                        description
                            "Operational data for static route with interface name";
                        uses rib-ipv4-interface-config;
                    } // END of state-container definition.
                } // End of interface-route-list

                list multicast-route {
                    key "source-prefix protocol-type";
                    description
                        "Mroute vrf";
                    leaf source-prefix  {
                        type  leafref {
                            path  "../config/source-prefix";
                        }
                        description "Source prefix";
                    } // END of source-prefix definition.

                    leaf protocol-type  {
                        type  leafref {
                            path  "../config/protocol-type";
                        }
                        description "mroute prototype";
                    } // END of protocol-type definition.

                    container config {
                        description
                            "configuration attributes for IPV4 static mroute";
                        uses ipi-rib-common:rib-ipv4-multicast-config;
                    } // END of config-container definition.
                    container state {
                        config false;
                        description
                            "Operational data for IPV4 static mroute";
                        uses ipi-rib-common:rib-ipv4-multicast-config;
                    } // END of state-container definition.
                } // End of multicast-route-list
            } // END of ipv4-container definition.
            container ipv6 {
                if-feature feature-list:HAVE_IPV6;
                description
                    "IPV6 Static Route configurations";

                list route {
                    key "destination-prefix gateway-address";
                    description
                        "RIB IPv6 destination prefix";
                    leaf destination-prefix  {
                        type  leafref {
                            path  "../config/destination-prefix";
                        }
                        description "IPv6 destination prefix (e.g. 3ffe:506::/32)";
                    } // END of destination-prefix definition.

                    leaf gateway-address  {
                        type  leafref {
                            path  "../config/gateway-address";
                        }
                        description "Use this attribute to create an IPv6 static route for a subnet.";
                    } // END of gateway-address definition.

                    container config {
                        description
                            "configuration attributes for IPV6 static route with gateway";
                        uses rib-bfd-config;
                        uses rib-ipv6-gateway-config;
                    } // END of config-container definition.
                    container state {
                        config false;
                        description
                            "Operational data for IPV6 static route with gateway";
                        uses rib-bfd-config;
                        uses rib-ipv6-gateway-config;
                    } // END of state-container definition.
                } // End of route-list

                list interface-route {
                when " /ipi-interface:interfaces/ipi-interface:interface/ipi-interface:config/ipi-interface:enable-switchport != '1' ";
                    key "destination-prefix interface-name";
                    description
                        "RIB IPv6 static route with interface name";
                    leaf destination-prefix  {
                        type  leafref {
                            path  "../config/destination-prefix";
                        }
                        description "IPv6 destination prefix (e.g. 3ffe:506::/32)";
                    } // END of destination-prefix definition.

                    leaf interface-name  {
                        type  leafref {
                            path  "../config/interface-name";
                        }
                        description "Use this attribute to create an IPv6 static route where nexthop is
                                    interface name.";
                    } // END of interface-name definition.

                    container config {
                        description
                            "configuration attributes for IPV6 static route with interface name";
                        uses rib-ipv6-interface-config;
                    } // END of config-container definition.
                    container state {
                        config false;
                        description
                            "Operational data for IPV6 static route with interface name";
                        uses rib-ipv6-interface-config;
                    } // END of state-container definition.
                } // End of interface-route-list

                list gateway-interface-route {
                when " /ipi-interface:interfaces/ipi-interface:interface/ipi-interface:config/ipi-interface:enable-switchport != '1' ";
                    key "destination-prefix gateway-address interface-name";
                    description
                        "RIB IPv6 static route with gateway and interface name";
                    leaf destination-prefix  {
                        type  leafref {
                            path  "../config/destination-prefix";
                        }
                        description "IPv6 destination prefix (e.g. 3ffe:506::/32)";
                    } // END of destination-prefix definition.

                    leaf gateway-address  {
                        type  leafref {
                            path  "../config/gateway-address";
                        }
                        description "IPv6 gateway address";
                    } // END of gateway-address definition.

                    leaf interface-name  {
                        type  leafref {
                            path  "../config/interface-name";
                        }
                        description "Use this attribute to create an IPv6 static route where nexthop is
                                    interface name and ipv6 prefix.";
                    } // END of interface-name definition.

                    container config {
                        description
                            "configuration attributes for IPV6 static route with gateway and
                                    interface name";
                        uses rib-ipv6-gateway-interface-config;
                    } // END of config-container definition.
                    container state {
                        config false;
                        description
                            "Operational data for IPV6 static route with gateway and interface name";
                        uses rib-ipv6-gateway-interface-config;
                    } // END of state-container definition.
                } // End of gateway-interface-route-list

                list multicast-route {
                when " /ipi-rib:routing/ipi-rib:static-routes/ipi-rib:ipv6/ipi-rib:multicast-route/ipi-rib:nexthop/ipi-rib:config/ipi-rib:gateway-mroute ";
                    key "source-prefix protocol-type";
                    description
                        "ipv6 mroute vrf";
                    leaf source-prefix  {
                        type  leafref {
                            path  "../config/source-prefix";
                        }
                        description "Source prefix";
                    } // END of source-prefix definition.

                    leaf protocol-type  {
                        type  leafref {
                            path  "../config/protocol-type";
                        }
                        description "mroute prototype";
                    } // END of protocol-type definition.

                    container config {
                        description
                            "configuration attributes for IPV6 static mroute";
                        uses ipi-rib-common:rib-ipv6-multicast-config;
                    } // END of config-container definition.
                    container state {
                        config false;
                        description
                            "Operational data for IPV6 static mroute";
                        uses ipi-rib-common:rib-ipv6-multicast-config;
                    } // END of state-container definition.
                    container nexthop {
                        description
                            "ipv6 mroute nexthop information";
                        container config {
                            presence "yes";
                            description
                                "configuration attributes for IPV6 static mroute gateway";
                            uses ipi-rib-common:rib-ipv6-multicast-gateway-config;
                        } // END of config-container definition.
                        container state {
                            config false;
                            description
                                "Operational data for IPV6 static mroute";
                            uses ipi-rib-common:rib-ipv6-multicast-gateway-config;
                        } // END of state-container definition.
                    } // END of nexthop-container definition.
                } // End of multicast-route-list
            } // END of ipv6-container definition.
        } // END of static-routes-container definition.
        container interfaces {
            description
                "RIB BFD interface related operations";

            list interface {
            when " /ipi-rib:routing/ipi-rib:interfaces/ipi-rib:interface/ipi-rib:bfd/ipi-rib:config/ipi-rib:ipv4-enable-bfd  or /ipi-rib:routing/ipi-rib:interfaces/ipi-rib:interface/ipi-rib:bfd/ipi-rib:config/ipi-rib:ipv6-enable-bfd ";
                if-feature feature-list:HAVE_BFD;
                key "name";
                description
                    "RIB BFD interface related operations";
                leaf name  {
                    type  leafref {
                        path  "/ipi-interface:interfaces/ipi-interface:interface/ipi-interface:name";
                    }
                    description "Reference to the base interface name";
                } // END of name definition.

                container bfd {
                    if-feature feature-list:HAVE_BFD;
                    description
                        "configuration attributes related to BFD for RIB";
                    container config {
                        description
                            "configuration attributes related to BFD for RIB";
                        uses rib-interface-bfd-config;
                    } // END of config-container definition.
                    container state {
                        config false;
                        description
                            "Operational data related to BFD for RIB";
                        uses rib-interface-bfd-config;
                    } // END of state-container definition.
                } // END of bfd-container definition.
            } // End of interface-list
        } // END of interfaces-container definition.
    } // END of routing-container definition.
    } // END of routing-grouping definition.

    uses routing-grouping;

    rpc rib-snmp-restart {
        description "Use rib-snmp-restart to restart SNMP in Routing Information Base (RIB)";
    }

    rpc clear-ip-stale-kernel-routes {
        description "Use clear-ip-stale-kernel-routes to clear stale IPv4 routes from the
                    RIB (Routing Information Base) and FIB (Forwarding Information Base).";
    }

    rpc clear-ipv6-stale-kernel-routes {
        description "Use clear-ipv6-stale-kernel-routes to clear stale IPv6 routes from the
                    RIB (Routing Information Base) and FIB (Forwarding Information Base).";
    }

    rpc clear-ip-route-all {
        description "Use clear-ip-route-all to clear all IPv4 routes";
    }

    rpc clear-ip-route {
        description "Use clear-ip-route to clear any specific IPv4 prefix route";
        input  {
            leaf prefix-address  {
                type inet:ipv4-prefix;
                mandatory true;
                description "Prefix to be cleared(e.g. 10.0.0.0/8)";
            }
        }
    }

    rpc clear-ipv6-route-all {
        description "Use clear-ipv6-route-all to clear all IPv6 routes";
    }

    rpc clear-ipv6-route {
        description "Use clear-ipv6-route to clear any specific IPv6 prefix route";
        input  {
            leaf prefix-ipv6-address  {
                type inet:ipv6-prefix;
                mandatory true;
                description "Prefix to be cleared(e.g. 3ffe:506::/32)";
            }
        }
    }

    rpc rib-debug-on {
        description "Use rib-debug-on to enable rib debugging";
        input  {
            leaf debug-options  {
                type ipi-rib-types:rib_debug_type_t;
                mandatory true;
                description "Debug-option to be enabled";
            }
        }
    }

    rpc rib-debug-off {
        description "Use rib-debug-off to disable rib debugging";
        input  {
            leaf debug-options  {
                type ipi-rib-types:rib_debug_type_t;
                mandatory true;
                description "Debug-option to be disabled";
            }
        }
    }

    rpc rib-ip-routing-debug-on {
        description "Use rib-ip-routing-debug-on to enable rib debugging for ipv4 route
                    add/delete/modify events";
        input  {
            leaf debug-route-options  {
                type ipi-rib-types:rib_debug_routing_type_t;
                mandatory true;
                description "Debug-route-option to be enabled";
            }
        }
    }

    rpc rib-ip-routing-debug-off {
        description "Use rib-ip-routing-debug-off to disable rib debugging for ipv4 route
                    add/delete/modify events";
        input  {
            leaf debug-route-options  {
                type ipi-rib-types:rib_debug_routing_type_t;
                mandatory true;
                description "Debug-route-option to be disabled";
            }
        }
    }

    rpc rib-ipv6-routing-debug-on {
        description "Use rib-ipv6-routing-debug-on to enable rib debugging for ipv6 route
                    add/delete/modify events";
        input  {
            leaf debug-route-options  {
                type ipi-rib-types:rib_debug_routing_type_t;
                mandatory true;
                description "Debug-route-option to be enabled";
            }
        }
    }

    rpc rib-ipv6-routing-debug-off {
        description "Use rib-ipv6-routing-debug-off to disable rib debugging for ipv6 route
                    add/delete/modify events";
        input  {
            leaf debug-route-options  {
                type ipi-rib-types:rib_debug_routing_type_t;
                mandatory true;
                description "Debug-route-option to be disabled";
            }
        }
    }

}

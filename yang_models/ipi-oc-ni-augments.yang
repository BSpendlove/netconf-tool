module ipi-oc-ni-augments {
  namespace   "http://www.ipinfusion.com/yang/ocnos/ipi-oc-ni-augments";
  prefix "ipi-oc-ni-augments";

  import openconfig-network-instance { prefix oc-netinst; }
  import openconfig-network-instance-types { prefix oc-ni-types; }

  revision "2021-04-26" {
    description "Add route-target configuration";
  }

  revision "2021-04-10" {
    description "Add bridge protocol";
  }

  revision "2021-02-25" {
    description "Initial Revision";
  }

  typedef  rt_direction_t {
    type enumeration {
      enum IMPORT { value 1; }
      enum EXPORT { value 2; }
      enum BOTH { value 3; }
    }
  }

  typedef  rt_rd_string_t {
    type string {
      pattern ".*:.*";
    }
  }

  augment "/oc-netinst:network-instances/oc-netinst:network-instance" {
    container route-targets {
      list route-target {
        when "../../oc-netinst:config/oc-netinst:route-distinguisher";
        key "rt-rd-string";
        description "Route target information";
        leaf rt-rd-string  {
          type  leafref {
            path  "../config/rt-rd-string";
          }
        }
        container config {
          leaf rt-rd-string  {
            description "Assign route target (RT) for the VRF.";
            type rt_rd_string_t;
          }
          leaf direction  {
            description
              "Determine if the route-target should be imported or exported from VRF";
            mandatory true;
            type rt_direction_t;
          }
        }
        container state {
          config false;
          leaf rt-rd-string  {
            description "Assign route target (RT) for the VRF";
            type rt_rd_string_t;
          }
          leaf direction  {
            description
              "Determine if the route-target should be imported or exported from VRF";
            type rt_direction_t;
          }
        }
      }
    }
  }

  augment "/oc-netinst:network-instances/oc-netinst:network-instance/oc-netinst:table-connections/oc-netinst:table-connection/oc-netinst:config" {

    description "Adds protocol instance id support for table connections";

    leaf dst-instance {
        type string;
        description "Instance ID of the destination protocol instance";
    }
  }

  augment "/oc-netinst:network-instances/oc-netinst:network-instance/oc-netinst:config" {
    leaf bridge-protocol {
      description "Bridge protocol type";
      when "../oc-netinst:type = 'oc-ni-types:L2L3'";
      default "ieee-vlan-bridge";

      type enumeration {
        enum ieee {
          value 1;
          description "IEEE 801.1Q spanning-tree protocol";
        }
        enum ieee-vlan-bridge {
          value 2;
          description "IEEE 801.1Q spanning-tree protocol,Vlan aware bridge";
        }
        enum rstp {
          value 3;
          description "IEEE 801.1w rapid spanning-tree protocol";
        }
        enum rstp-vlan-bridge {
          value 4;
          description "IEEE 801.1w rapid spanning-tree protocol,Vlan aware bridge";
        }
        enum mstp {
          value 5;
          description "IEEE 802.1s multiple spanning-tree protocol";
        }
        enum provider-rstp {
          value 6;
          description "IEEE 802.1s multiple spanning-tree protocol";
        }
        enum provider-mstp {
          value 7;
          description "IEEE 802.1s rapid spanning-tree protocol";
        }
        enum rpvst+ {
          value 8;
          description "IEEE 801.1w rapid per vlan spanning-tree protocol";
        }
        enum rstp-ring {
          value 10;
          description "IEEE 801.1w rapid spanning-tree protocol,Enable Rapid Ring spanning-tree";
        }
        enum mstp-ring {
          value 11;
          description "IEEE 802.1s multiple spanning-tree protocol,Enable Rapid Ring spanning-tree";
        }
        enum provider-rstp-edge {
          value 12;
          description "IEEE 802.1s multiple spanning-tree protocol,Configure as Edge bridge";
        }
        enum provider-mstp-edge {
          value 13;
          description "IEEE 802.1s rapid spanning-tree protocol,Configure as Edge bridge";
        }
        enum rstp-vlan-bridge-ring {
          value 14;
          description "IEEE 801.1w rapid spanning-tree protocol,Vlan aware bridge,Enable Rapid Ring spanning-tree";
        }
        enum trill {
          value 20;
          description "Transparent Interconnection of Lots of Link";
        }
        enum evb {
          value 97;
          description "evb";
        }
        enum svlan-evb {
          value 98;
          description "Svlan aware evb";
        }
      }
    }
  }
}
